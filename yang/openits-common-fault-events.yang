module openits-common-fault-events {
  yang-version 1.1;
  namespace "urn:openits:yang:common-fault-events";
  prefix openits-common-fault;

  import openits-types {
    prefix openits-types;
  }
  import ietf-yang-types {
    prefix yang;
  }

  organization
    "OpenITS Working Group (proposal)";

  contact
    "OpenITS Working Group (proposal)";

  description
    "Cross-service fault-raised and fault-cleared notifications. Each
     service derives its own fault-kind identities from
     openits-types:fault-event-kind (or its service-specific sub-base)
     and emits these generic notifications with the kind identityref
     identifying the specific fault.

     fault-raised announces a newly-active fault. fault-cleared
     announces resolution of a previously-active fault. Both carry
     the fault-id (free-form, decoder-controlled), severity, and
     wire-source. This module hosts only these two cross-service
     notifications; signal-controller HR-log fault transitions are
     carried by openits-signal-control-events:controller-fault-
     event instead.";

  openits-types:openits-version "0.4.0";

  revision 2026-10-14 {
    description
      "fault-raised composes the shared openits-types fault-entry, so it
       carries first-observed and an optional component, and may be
       re-emitted as an upsert. fault-cleared carries first-observed and
       the component. Breaking: first-observed is mandatory on both.";
    reference "RFC 7950 §7.13.";
  }
  revision 2026-10-13 {
    description
      "Inherit the mandatory sequence-epoch leaf from the openits-types
       event-header grouping, which changes every notification payload
       in this module. Breaking: producers must emit sequence-epoch.";
    reference "RFC 7950 §11.";
  }
  revision 2026-07-21 {
    description
      "Add optional 'correlates-with' to fault-raised (fault-id of a
       related active fault on the same source-device), mirroring the
       new openits-types:fault-entry leaf. Additive.
       - Collapse duplicate same-date revision statements.";
  }
  revision 2026-07-14 {
    description
      "Cut 3c: update prose references to the collapsed
       openits-signal-control-events companion (was 11 per-domain
       -events modules). Documentation only; no schema-node change.";
  }
  revision 2026-07-13 {
    description
      "Rewrite fault-raised and fault-cleared 'fault-id' descriptions
       to state the condition-scoped contract explicitly (stable
       across raise/clear of the SAME fault condition on the same
       source-device; the pair (source-device-id, fault-id) is unique
       among a device's currently-active faults; reused on re-raise;
       distinct simultaneous instances of the same condition get
       distinct fault-ids), matching openits-types:fault-entry's
       fault-id contract. Documentation-only — type remains string,
       no new constraint. Align fault-raised severity leaf description
       with the fault-severity typedef (defer to it; drop the stale
       'informational' phrasing).

      Adopt the shared openits-types:event-header grouping in
       fault-raised and fault-cleared, replacing the inline
       source-device-id + occurred-at leaf pair. Wire-stable:
       field names/types unchanged, proto field numbers preserved.";
  }
  revision 2026-07-12 {
    description
      "Move controller-fault-event to openits-signal-control-events
       (it is signal-control-specific, not cross-service). This module
       now hosts only the cross-service fault-raised/fault-cleared.
       Resolves the catalog over-fan.";
  }
  revision 2026-07-10 {
    description
      "Delete the local 'fault-severity' typedef and repoint both
       severity leaves to the shared openits-types:fault-severity
       typedef. Member set and order unchanged (info/warning/minor/
       major/critical) — wire-stable. Part of the cross-module
       fault-severity consolidation.";
  }
  revision 2026-05-19 {
    description
      "Accept controller-fault-event migration from openits-signal-
       control-notifications@2026-05-15. Adds a third notification
       (controller-fault-event) for HR-level controller fault
       transitions; distinct from fault-raised/fault-cleared which
       carry NTCIP-polled fault state.";
  }
  revision 2026-05-18 {
    description
      "Accept fault-raised migration from openits-signal-control-
       notifications@2026-05-15. The existing fault-raised notification
       shape is already compatible (kind + fault-id + severity +
       wire-source); this revision is a documentation bump to record
       that signal-control's fault-raised now lives here.";
  }
  revision 2026-05-17 {
    description
      "Add descriptions to source-device-id, severity, occurred-at,
       and the fault-cleared leaves so the notification contract is
       self-documenting for Phase 0c decoder implementers.";
  }
  revision 2026-05-16 {
    description "Initial revision.";
  }

  /* --------------------------------------------------------------
   * Notifications
   * -------------------------------------------------------------- */

  notification fault-raised {
    openits-types:arc-it-flow
      "Device -> Maintenance : fault data";
    description
      "A fault condition became active on a device. Subsequent
       fault-cleared with the same fault-id announces resolution. A
       producer MAY re-emit fault-raised with the same fault-id as an
       upsert, for a resync or a severity change.";

    leaf kind {
      type identityref { base openits-types:fault-event-kind; }
      mandatory true;
      description
        "Specific fault class. Service-derived (e.g.,
         openits-signal-control-types:fault-power-failure) or
         vendor-derived (e.g., openits-vendor-econolite-signal-
         control-types:econolite-vendor-alarm-1).";
    }

    uses openits-types:event-header;

    uses openits-types:fault-entry {
      refine "fault-id" {
        mandatory true;
      }
      refine "severity" {
        mandatory true;
      }
    }

    uses openits-types:wire-source;
  }

  notification fault-cleared {
    openits-types:arc-it-flow
      "Device -> Maintenance : fault data";
    description
      "A previously-raised fault is no longer active. fault-id
       matches the corresponding fault-raised.";

    leaf kind {
      type identityref { base openits-types:fault-event-kind; }
      mandatory true;
      description
        "Same fault class identity as the corresponding fault-raised
         (see fault-raised/kind for the derivation rules).";
    }

    uses openits-types:event-header;

    leaf fault-id {
      type openits-types:fault-id;
      mandatory true;
      description
        "Device-local fault identifier, condition-scoped: stable across
         raise/clear of the same fault condition on the same
         source-device. The pair (source-device-id, fault-id) is unique
         among a device's currently-active faults. Re-raising a condition
         after it cleared reuses the same fault-id. If the same condition
         has multiple simultaneous distinct instances, each gets a
         distinct fault-id (e.g. a suffix). Consumers correlate/dedupe on
         (source-device-id, fault-id). Matches the corresponding
         fault-raised.";
    }

    leaf first-observed {
      type yang:date-and-time;
      mandatory true;
      description
        "first-observed of the fault being cleared, so a consumer can
         match the clear to the occurrence it ends.";
    }

    uses openits-types:component-ref;

    uses openits-types:wire-source;
  }
}
