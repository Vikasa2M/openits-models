module openits-signal-control-types {
  yang-version 1.1;
  namespace "urn:openits:yang:signal-control-types";
  prefix openits-sc-types;

  import openits-types {
    prefix openits-types;
  }

  organization
    "OpenITS Working Group (proposal)";

  contact
    "OpenITS Working Group (proposal)";

  description
    "Signal-control event-kind identity hierarchy. Derives from the
     cross-service openits-types:device-event-kind root. Identities
     here cover the ATSPM 'Indiana enumeration' codes that signal
     controllers emit on the wire; the notification companion module
     (openits-signal-control-events) carries identityref leaves
     pointing into this hierarchy.

     New identities are additive. Removing or renaming an identity
     is a breaking change and requires a major revision bump.

     Copyright (c) 2026. Distributed under Apache 2.0.";

  openits-types:openits-version "0.15.0";

  revision 2026-10-12 {
    description
      "Let detector and monitor faults be raised as what they are, and
       correct the flash-cause and monitor definitions.

       - vehicle-detector-fault-* now also derive from sc-fault-detector,
         and monitor-fault-type from sc-fault-event-kind, so fault-raised
         and faults/fault can carry a stuck-on loop or a red-fail as
         itself. Previously a red-fail could only be raised as
         sc-fault-conflict. Additive.
       - flash-mmu-conflict maps unitFlashStatus mmu(6), which NTCIP 1202
         v04 renames smu(6): flash forced by ANY cabinet signal monitor
         (TS2 MMU, TS1 conflict monitor, ITS-cabinet CMU) for any
         monitored condition, not only a conflict.
       - flash-fault-monitor maps faultMonitor(5), renamed
         controllerFaultFlash(5): flash the controller unit started on a
         fault it detected itself. It no longer claims TS1 and ITS-cabinet
         monitor flash, which is mmu(6). Producers that sent those cases
         here should send flash-mmu-conflict.
       - monitor-red-fail is the absence of any indication on a channel,
         not a conflict; monitor-dual-indication covers any two of green,
         yellow and red on one channel.";
    reference "NTCIP 1202:2019 §5 (unitFlashStatus); NTCIP 1202 v04 §5.4.6; NEMA TS2-2021 section 4.";
  }
  revision 2026-09-08 {
    description
      "Identity-vs-enum corrections (breaking, pre-1.0).

       time-source moves to openits-types, unchanged in shape: the RSU
       modeled the same axis as a disjoint closed enum, so the foundation
       now holds one vocabulary both services derive from. Migration:
       openits-signal-control-types:time-source-* becomes
       openits-types:time-source-*, member for member.

       priority-type becomes an identity. It was a closed enum carrying
       an 'other' escape hatch, which is the tell that the axis is open:
       agencies grant signal priority to classes the core has not
       catalogued (school buses, plows, refuse fleets on a winter
       schedule), and preemption-type beside it became an identity for
       exactly this reason in 2026-07-21. Migration: none -> absent leaf,
       transit -> priority-transit, freight -> priority-freight,
       other -> priority-other; priority-emergency is new, for a request
       that biases the sequence without seizing it the way
       preempt-emergency-vehicle does.

       coordination-cycle-state becomes an identity too, one day after
       being added as an enum. Transition method is vendor territory --
       shortway and adaptive transitions ship beyond the classic
       add/subtract/dwell set -- and controller-mode beside it was
       already an identity on the same reasoning. Two altitudes:
       cycle-state-persistent for the states a poller can sample, with
       the three instantaneous HR markers deriving from the root
       directly, so the polled readback in openits-signal-control
       narrows by type rather than by a prose caveat. Migration:
       free -> cycle-free, in-step -> cycle-in-step, transition-* ->
       cycle-transition-*, local-zero -> cycle-local-zero,
       begin-pickup -> cycle-begin-pickup,
       master-cycle-zero -> cycle-master-cycle-zero.";
    reference "NTCIP 1211 (priority-class / PRS request semantics); RFC 7950 §11.";
  }
  revision 2026-09-07 {
    description
      "Cabinet-neutral flash and monitor taxonomy (breaking, pre-1.0).

       flash-cause could not name an NTCIP unitFlashStatus
       faultMonitor(5) flash, so every cabinet whose monitor is not a
       TS2 MMU -- a TS1 conflict monitor, an ITS-cabinet CMU -- had to
       be reported as either flash-mmu-conflict (names hardware the
       cabinet does not contain) or flash-automatic (loses the fact that
       a monitor forced the flash, which is the one safety-relevant
       thing in the event). Adds flash-fault-monitor for that case and
       flash-other for unitFlashStatus other(1), and states which NTCIP
       value each existing member maps to.

       Removes flash-exit: exiting flash is not a flash cause, it is a
       mode transition, and it is reported as such by
       openits-common-mode-events:mode-changed with a current mode of
       mode-free or mode-coordinated.

       Renames mmu-fault-type to monitor-fault-type and its members
       mmu-* to monitor-*. The monitored conditions (red-fail,
       dual-indication, conflict, clearance, CVM, +24V) are common to
       every cabinet monitor; only the unit fitted differs, so naming
       the axis after one cabinet family's hardware mislabeled the
       fault on every other. Adds monitor-field-check,
       monitor-port1-fail, monitor-diagnostic and monitor-watchdog,
       which TS2 MMUs and ITS-cabinet CMUs report and the model had no
       target for. Removes mmu-none: absence of an entry in the
       config-false monitor readback already means no active fault, and
       a value meaning 'no value' forces every consumer to special-case
       it.

       BREAKING (pre-1.0): identityref values are wire strings, so
       renamed identities change what conforming producers emit, and
       removed identities become unrepresentable. Proto tags are
       unaffected (identityrefs render as strings).

       Also in this revision:

       Re-bases the four HR fault identities (fault-unit-flash-status,
       fault-unit-alarm-group-1, fault-power-failure,
       fault-vendor-alarm) onto controller-fault-event-kind, which had
       no derived identities at all despite its own description and
       controller-fault-event's naming it as their parent -- so the
       documented filter derived-from-or-self(kind,
       'controller-fault-event-kind') matched nothing. They still derive
       from sc-fault-event-kind through it, so every existing filter
       keeps matching and no wire string changes.

       Adds the ATSPM codes whose absence forced real measures to fall
       through to unmapped-event: phase-barrier-termination (31),
       overlap-fya-begin-permissive / -end-permissive (32/33, without
       which protected and permissive left-turn service cannot be
       separated on the dominant US left-turn treatment), and
       controller-clock-updated (181, under sc-comm-health-event-kind,
       which until now had no derived identity and no user -- a clock
       step invalidates every duration-based measure spanning it).

       Adds four detector-fault identities matching NTCIP
       vehicleDetectorReportedAlarms (no-activity, max-presence,
       erratic-count, communications). The controller diagnoses these
       from thresholds the core already configures, but the model had
       only the coarse sc-fault-detector to report them with -- a
       stuck-on loop, the most common detector work order, was
       indistinguishable from any other detector fault.

       Adds the coordination-cycle-state typedef, the HR-log cycle-state
       vocabulary the coordination-change notification adopts in place
       of a bare integer. All additive.";
    reference
      "NTCIP 1202:2019 §5 (unitFlashStatus); NEMA TS2-2021 section 4;
       ATC Cabinet Standard (CMU).";
  }
  revision 2026-08-05 {
    description
      "Model-review remediation (2026-08): correct mmu-cvm to the CVM
       controller-health input (it previously conflated CVM with the
       +24V supply monitor — different hardware to troubleshoot) and add
       a distinct mmu-24v identity for the +24V Monitor inputs.
       Identity addition; non-breaking. Widen the plan-id typedef
       description to cover its sequence-id reuse (doc-only).";
    reference "NEMA TS2-2021 section 4.";
  }
  revision 2026-07-21 {
    description
      "Model-review remediation (2026-07):
       - Add shared cross-surface identifier typedefs (detector-channel,
         preempt-slot, plan-id, overlap-number) so the core config tree and
         the events companion type the same concepts identically and can be
         correlated.
       - Add the tsam-engagement-state typedef, shared by the
         tsam-mode-changed notification's prior/current leaves (removing a
         duplicated inline enum).
       - Correct the overlap-minus-green identity description: a minus-green
         overlap is SUPPRESSED (not extended) while its modifier phases are
         green (NTCIP minusGreenYellow).
       - BREAKING: replace the closed preemption-type enum with an open
         identity hierarchy (preempt-railroad / preempt-emergency-vehicle /
         preempt-other) so vendors/agencies can derive new preemption sources
         (drawbridge, emergency-gate) without a core change.
       - Collapse duplicate same-date revision statements.";
    reference
      "NTCIP 1202:2019 §5; NTCIP 1211; NEMA TS-2 §4; MUTCD 11th ed. Ch. 8C.";
  }
  revision 2026-07-14 {
    description
      "Cut 3c: update prose references to the collapsed
       openits-signal-control-events companion (was 11 per-domain
       -events modules). Documentation only; no schema-node change.

      Config completeness cut 2d (timebase): add the time-source identity
       hierarchy (ntp / gnss / cellular / line-frequency / manual) backing the
       new openits-signal-control timebase/clock/time-source leaf. An identity
       so vendors can derive newer sources (PTP, GNSS variants) without a core
       revision. Additive.

      Config completeness cut 2c (mode collapse): remove the mode-normal
       identity and fold its meaning into mode-free, the single
       uncoordinated-actuated mode (NTCIP and signal techs treat normal and free
       as one mode). Coordinated-but-transitioning is reported by the core's new
       coordination/state/cycle-state leaf. BREAKING: consumers keyed on
       mode-normal switch to mode-free.

      Add overlap-type and channel-movement identity hierarchies for the
       signal-control overlaps and channel-table config (cut 2b). Both are
       vendor-extensible axes (FYA/bicycle overlap variants; bicycle
       signal faces), so identities rather than enums. Additive.";
    reference
      "NTCIP 1201 (global time / time-base).;
      NTCIP 1202 v03 (controller operating modes).;
      NTCIP 1202:2019 §5 (overlapTable / channelTable).";
  }
  revision 2026-07-13 {
    description
      "Add the detector-type identity hierarchy (base detector-type +
       inductive-loop / video / radar / magnetometer / ped-pushbutton /
       ped-passive / bicycle / emergency-vehicle / transit) so detection
       technology is a vendor-extensible axis: a vendor module derives a
       newer technology (lidar, thermal, BSM-derived) without a core
       change. Backs the openits-signal-control detector config/type leaf,
       which moves from a closed enum to this identityref. Additive.

      Add tsp-request-denied and tsp-request-aborted identities under
       sc-tsp-event-kind for NTCIP 1211 Priority Request Server
       rejected/aborted outcomes; tsp-request-denied pairs with the
       tsp-event denial-reason leaf. Additive.

       Split preemption-type into preemption classes only (none,
       railroad, emergency-vehicle, other) and a new priority-type
       typedef (none, transit, freight, other) for the NTCIP 1211
       priority axis, so an active rail preemption and an active
       transit priority request are separately representable instead
       of sharing one enumeration. BREAKING (pre-v1): removes the
       transit-priority and freight-priority members from
       preemption-type — consumers using either value must switch to
       priority-type's transit/freight members.

       Follow-up: preemption-type's 'other' member is reassigned from
       value 3 to value 5, since 3 was the former transit-priority
       slot vacated by this same split — leaving 'other' there would
       let a stale binary-encoded 3 silently misdecode as 'other'.
       Values 3 and 4 are now retired gaps and must not be reused.

      Extend the mode-flash identity description: it stays a single
       mode value (does not split by cause); note the cause is carried
       instead by the state tree's flash-cause leaf and by
       mode-changed's trigger leaf, so consumers get it from either
       surface without splitting the mode taxonomy.

      Add flash-cause (flash-mmu-conflict/automatic/programmed-tod/
       manual/startup/preempt/exit) and mmu-fault-type (mmu-red-fail/
       dual-indication/conflict/clearance/cvm/none) identity sets.
       flash-cause backs the new config-false state-tree flash-cause
       leaf and the optional flash-cause on controller-fault-event
       (openits-signal-control-events); mmu-fault-type backs the
       state tree's mmu/fault-type leaf. Discriminates why an
       intersection is flashing (MMU conflict vs. programmed TOD vs.
       manual, etc.) — previously collapsed into a single boolean.
       Additive.

      Indiana taxonomy corrections + additions (wire-freeze pass),
       verified against Li, Hainen, Sturdevant et al., 'Indiana
       Traffic Signal Hi Resolution Data Logger Enumerations',
       Purdue TPF-5(377), Aug 2020 (supersedes the 2012 original):

       Corrections:
       - Rename phase-dark -> phase-inactive (Indiana 12 is 'Phase
         Inactive' — phase no longer active within the ring, solid
         red; there is no dark/unpowered semantic at this code. The
         genuinely dark-headed codes are the separate ped-dark,
         ped-overlap-dark, and overlap-dark identities). BREAKING
         rename — consumers keyed on the wire value 'phase-dark'
         (e.g. openits-collector) must update to 'phase-inactive'.
       - Rename phase-begin-red -> phase-end-red-clearance and
         correct its mapping: Indiana 11 is 'Phase End Red
         Clearance' (set when red-clearance timing concludes; only
         set if red clearance is served), not a generic 'phase is
         red' state. BREAKING rename — consumers keyed on the wire
         value 'phase-begin-red' (e.g. openits-collector) must
         update to 'phase-end-red-clearance'.
       - phase-skipped (Indiana 14) is unchanged: confirmed a
         directly-logged event in the 2020 revision (not merely
         inferred). Kept as code 14.
       - ped-oversized-served (Indiana 26) is unchanged in meaning;
         dropped the '(ADA)' parenthetical from its description —
         code 26 is a demand-driven extension, not an accessibility
         mechanism (that is Indiana 25, ped-extended-change-interval).

       Additions (all additive, non-breaking):
       - sc-phase-event-kind: phase-on (0), phase-check (2),
         phase-min-complete (3), phase-green-termination (7),
         phase-end-yellow (9), phase-omit-on (46), phase-omit-off (47).
       - sc-pedestrian-event-kind: ped-omit-on (48), ped-omit-off (49).
       - sc-coordination-event-kind: coord-cycle-state-change (150),
         coord-yield-point (151).
       - sc-external-io-event-kind: ext-io-manual-control-enable (178),
         ext-io-stop-time-input (180).

       Not added: cabinet-door / police-panel have no canonical
       Indiana wire code in either the 2012 or 2020 enumeration;
       omitted rather than inventing one.

      Add sc-detector-report (sc-detector-event-kind +
       openits-types:report-event-kind), sc-plan-applied
       (sc-coordination-event-kind only — a discrete coordination
       event, not a periodic report), and sc-operational-status-report
       (signal-control-event-kind + openits-types:report-event-kind)
       identities: the 'kind' values for detector-report, plan-applied,
       and operational-status-report (all now in
       openits-signal-control-events) now that each carries the
       unified event-header + kind contract. Additive.

      Add sc-unmapped-event identity under signal-control-event-kind,
       the 'kind' value for openits-signal-control-events:
       unmapped-event now that it carries the unified event-header +
       kind contract. Additive.

      Add seven state-tree fault-category identities under
       sc-fault-event-kind (sc-fault-detector/lamp/conflict/
       communication/power/cabinet/software) for the openits-signal-
       control config-false faults list, which moves from an inline
       enumeration to an identityref. Parallel to the
       per-service fault-category identities in the other -types
       modules. Additive.

       Convert controller-mode from a closed enumeration to an identity
       hierarchy (controller-mode base + mode-normal/coordinated/free/
       flash/preempt/priority/manual/off) so a vendor can derive a
       proprietary mode without a core change. Wire form is the identity
       name. controller-mode also derives from
       openits-types:operational-mode so its values can be carried in
       the generic mode-changed prior/current identityref.";
    reference
      "NTCIP 1202:2019 §5 (vehicleDetectorTable).;
      NTCIP 1202 v03 (preemption-type); NTCIP 1211 (priority-type, PRS outcomes).;
      NEMA TS2-2021 section 4; Indiana 173 (fault-unit-flash-status).;
      Li, H., A.M. Hainen, J.R. Sturdevant, et al. Indiana Traffic
       Signal Hi Resolution Data Logger Enumerations. Purdue TPF-5(377),
       Aug 2020 (doi: 10.5703/1288284316998), supersedes the Nov 2012
       original (doi: 10.4231/K4RN35SH).";
  }
  revision 2026-07-12 {
    description
      "Drop the now-dangling openits-types:<x>-event-kind base from
       the 9 sc-<x>-event-kind identities (phase, detector, overlap,
       pedestrian, preemption, coordination, tsp, tsam, external-io):
       openits-types removed those 9 first-level bases from
       device-event-kind in the same revision (they were never
       cross-service). Each sc-<x>-event-kind now derives solely
       from signal-control-event-kind; the behavioral grouping they
       express is carried entirely within this module. sc-fault-
       event-kind, sc-mode-event-kind, and sc-comm-health-event-kind
       keep their dual base — fault/mode/comm-health-event-kind
       remain genuinely cross-service in openits-types. Breaking
       change (RFC 7950 §11) — bases removed. No wire-facing
       enumeration, notification, or generated field is affected:
       sc-<x>-event-kind identities keep their names and values.

       Same-day: repoint the controller-fault-event-kind doc-ref to
       openits-signal-control-events, since
       controller-fault-event moved there from
       openits-common-fault-events.";
  }
  revision 2026-05-23 {
    description
      "Two same-day changes:
       - Move preemption-type and controller-mode typedefs from
         openits-signal-control into this -types module. Sub-event
         modules and notification companions now reference both
         typedefs via openits-sc-types: rather than openits-sc:,
         so they no longer need to import the service core. Wire
         format unchanged; consumers re-import under the new prefix.
       - Re-base sc-tsam-event-kind from sc-tsp-event-kind to
         openits-types:tsam-event-kind + signal-control-event-kind
         (peer-level dual classification). TSAM is agency-side
         adaptive optimization, not transit priority; the prior
         hierarchy conflated two distinct domains.";
  }
  revision 2026-05-18 {
    description
      "Phase 0c migration support:
       - Add controller-fault-event-kind identity for HR-level
         controller fault events (distinct from sc-fault-event-kind
         which covers cabinet-level faults).
       - Add sc-tsam-event-kind, tsam-mode-changed, and
         tsam-recommendation-applied identities for the TSAM
         notifications migrated to openits-signal-control-events.";
  }
  revision 2026-05-16 {
    description
      "Initial revision. Covers the ~90 Indiana enumeration codes
       currently mapped by internal/atspm/decoders/indianamap. Codes
       in the dropped-on-decode list (200+, 600+, 1200+, vendor-
       specific bands) are not yet represented; they land in future
       phases of the event-taxonomy expansion.";
    reference "ATSPM Indiana enumeration (HR event-code vocabulary).";
  }

  /* --------------------------------------------------------------
   * First-level bases (one per behavioral class)
   * -------------------------------------------------------------- */

  identity signal-control-event-kind {
    base openits-types:device-event-kind;
    description
      "Root for signal-controller events. Behavioral-class sub-bases
       (phase, detector, overlap, pedestrian, preemption, coordination,
       tsp, external-io, fault, mode, comm-health) derive from this.";
  }

  identity sc-unmapped-event {
    base signal-control-event-kind;
    description
      "A raw controller HR-log row with no mapped openits event identity yet —
       carried verbatim (wire-source) for lossless replay.";
  }

  /* Signal-control behavioral sub-bases under signal-control-event-kind,
   * so consumers can filter 'all signal-control events' vs 'all events
   * everywhere'. Identityref uses the most-derived match.
   *
   * Two patterns coexist:
   *  - Signal-control-only classes (phase, detector, overlap, pedestrian,
   *    preemption, coordination, tsp, tsam, external-io): sc-{kind} derives
   *    ONLY from signal-control-event-kind. There is no cross-service
   *    openits-types:{kind}-event-kind base (those were re-homed here).
   *  - Cross-service classes (fault, mode, comm-health): sc-{kind} derives
   *    from BOTH openits-types:{kind}-event-kind AND signal-control-event-kind,
   *    since the behavioral root is shared across services.
   * Identities below derive from the matching sc-{kind}.
   */

  identity sc-phase-event-kind {
    base signal-control-event-kind;
    description "Signal-control phase events.";
  }

  identity sc-detector-event-kind {
    base signal-control-event-kind;
    description "Signal-control vehicle/ped/TSP detector events.";
  }

  identity sc-overlap-event-kind {
    base signal-control-event-kind;
    description "Signal-control phase-overlap events.";
  }

  identity sc-pedestrian-event-kind {
    base signal-control-event-kind;
    description "Signal-control pedestrian-interval and ped-call events.";
  }

  identity sc-preemption-event-kind {
    base signal-control-event-kind;
    description "Signal-control preemption stage events.";
  }

  identity sc-coordination-event-kind {
    base signal-control-event-kind;
    description
      "Signal-control coordination events (splits, cycle, offset,
       pattern).";
  }

  identity sc-tsp-event-kind {
    base signal-control-event-kind;
    description
      "Signal-control Transit Signal Priority cycle + detail events.";
  }

  identity sc-tsam-event-kind {
    base signal-control-event-kind;
    description
      "TSAM (Traffic Signal Adaptive Management) events: mode
       transitions and applied recommendations. Behavioral class
       expressed solely via signal-control-event-kind now that
       tsam-event-kind no longer exists as a cross-service base.";
  }

  identity tsam-mode-changed {
    base sc-tsam-event-kind;
    description "TSAM engagement state changed.";
  }

  identity tsam-recommendation-applied {
    base sc-tsam-event-kind;
    description "TSAM produced a recommendation that was applied.";
  }

  identity sc-fault-event-kind {
    base openits-types:fault-event-kind;
    base signal-control-event-kind;
    description "Signal-control faults (cabinet, MMU, conflict-flash, etc.).";
  }

  identity sc-mode-event-kind {
    base openits-types:mode-event-kind;
    base signal-control-event-kind;
    description "Signal-control operational-mode transitions.";
  }

  identity sc-comm-health-event-kind {
    base openits-types:comm-health-event-kind;
    base signal-control-event-kind;
    description
      "Signal-control communication-health events. Placeholder
       sub-base; leaf identities (time-drift, comm-attempt-window,
       link-degraded/recovered) land in a future revision.";
  }

  identity sc-external-io-event-kind {
    base signal-control-event-kind;
    description
      "Signal-control external-I/O events (external calls, test
       inputs, special-function outputs). Indiana codes 178
       (ext-io-manual-control-enable) and 180 (ext-io-stop-time-input)
       are represented below; codes 171-172, 176-177, 179, 701-710
       remain a placeholder for a future revision.";
  }

  /* --------------------------------------------------------------
   * Phase events (Indiana codes 0-12, 14, 41-44, 46-47)
   * -------------------------------------------------------------- */

  identity phase-on {
    base sc-phase-event-kind;
    description
      "Indiana 0: phase on — set when NEMA Phase On becomes active,
       either upon start of green or walk interval, whichever occurs
       first.";
  }
  identity phase-begin-green {
    base sc-phase-event-kind;
    description "Indiana 1: phase began green.";
  }
  identity phase-check {
    base sc-phase-event-kind;
    description
      "Indiana 2: phase check — set when a conflicting call is
       registered against the active phase (marks the beginning of
       MAX timing).";
  }
  identity phase-min-complete {
    base sc-phase-event-kind;
    description "Indiana 3: phase minimum-green timer expired.";
  }
  identity phase-gap-out {
    base sc-phase-event-kind;
    description "Indiana 4: phase terminated by gap-out.";
  }
  identity phase-max-out {
    base sc-phase-event-kind;
    description "Indiana 5: phase terminated by max-out.";
  }
  identity phase-force-off {
    base sc-phase-event-kind;
    description "Indiana 6: phase terminated by force-off.";
  }
  identity phase-green-termination {
    base sc-phase-event-kind;
    description
      "Indiana 7: phase green termination — set when phase green
       indications are terminated into either the yellow change
       interval or a permissive (FYA) movement.";
  }
  identity phase-begin-yellow {
    base sc-phase-event-kind;
    description "Indiana 8: phase entered yellow-change interval.";
  }
  identity phase-end-yellow {
    base sc-phase-event-kind;
    description
      "Indiana 9: phase end yellow change — set when the phase
       yellow indication becomes inactive.";
  }
  identity phase-begin-red-clearance {
    base sc-phase-event-kind;
    description "Indiana 10: phase entered red-clearance interval.";
  }
  identity phase-end-red-clearance {
    base sc-phase-event-kind;
    description
      "Indiana 11: phase end red clearance — set when red-clearance
       timing concludes. Set only if phase red clearance is served;
       may not coincide with completion of the phase, e.g. during
       clearance of trailing overlaps, red revert timing, red rest,
       or delay for other ring terminations.";
  }
  identity phase-inactive {
    base sc-phase-event-kind;
    description
      "Indiana 12: phase inactive — phase is no longer active within
       the ring, including completion of any trailing overlaps or end
       of barrier delays for adjacent ring termination. Solid red;
       distinct from a dark/unpowered signal (see ped-dark,
       ped-overlap-dark, overlap-dark for the dark-headed codes).";
  }
  identity phase-skipped {
    base sc-phase-event-kind;
    description "Indiana 14: phase skipped in the sequence.";
  }
  identity phase-hold-active {
    base sc-phase-event-kind;
    description "Indiana 41: hold activated on phase.";
  }
  identity phase-hold-released {
    base sc-phase-event-kind;
    description "Indiana 42: hold released on phase.";
  }
  identity phase-call-registered {
    base sc-phase-event-kind;
    description "Indiana 43: call registered for phase.";
  }
  identity phase-call-dropped {
    base sc-phase-event-kind;
    description "Indiana 44: call dropped for phase.";
  }
  identity phase-omit-on {
    base sc-phase-event-kind;
    description
      "Indiana 46: phase omit on — set when phase omit is applied by
       the coordinator, preemptor, or other dynamic source. The phase
       does not necessarily need to be actively timing for this event
       to occur. Not set when the phase is removed from the active
       sequence or another configuration-level change occurs.";
  }
  identity phase-omit-off {
    base sc-phase-event-kind;
    description
      "Indiana 47: phase omit off — set when a previously applied
       phase omit is released. Not set when the phase is added to the
       active sequence or another configuration-level change occurs.";
  }

  /* --------------------------------------------------------------
   * Pedestrian events (Indiana codes 21-26, 45, 48-49, 67-70, 89-92)
   * -------------------------------------------------------------- */

  identity ped-begin-walk {
    base sc-pedestrian-event-kind;
    description "Indiana 21: pedestrian WALK interval began.";
  }
  identity ped-begin-change-interval {
    base sc-pedestrian-event-kind;
    description "Indiana 22: pedestrian change interval (FDW) began.";
  }
  identity ped-begin-solid-dont-walk {
    base sc-pedestrian-event-kind;
    description "Indiana 23: pedestrian solid DONT-WALK began.";
  }
  identity ped-dark {
    base sc-pedestrian-event-kind;
    description "Indiana 24: pedestrian indication dark.";
  }
  identity ped-extended-change-interval {
    base sc-pedestrian-event-kind;
    description "Indiana 25: pedestrian extended change interval.";
  }
  identity ped-oversized-served {
    base sc-pedestrian-event-kind;
    description
      "Indiana 26: oversized pedestrian served — set when the
       pedestrian phase is active beyond the pedestrian change
       interval or force-off point due to demand.";
  }
  identity ped-call-registered {
    base sc-pedestrian-event-kind;
    description "Indiana 45: pedestrian call registered.";
  }
  identity ped-omit-on {
    base sc-pedestrian-event-kind;
    description
      "Indiana 48: pedestrian omit on — set when pedestrian omit is
       applied by the coordinator, preemptor, or other dynamic
       source. Mirrors phase-omit-on for the pedestrian movement.";
  }
  identity ped-omit-off {
    base sc-pedestrian-event-kind;
    description
      "Indiana 49: pedestrian omit off — set when a previously
       applied pedestrian omit is released. Mirrors phase-omit-off
       for the pedestrian movement.";
  }
  identity ped-overlap-begin-walk {
    base sc-pedestrian-event-kind;
    description "Indiana 67: ped-overlap WALK began.";
  }
  identity ped-overlap-begin-clearance {
    base sc-pedestrian-event-kind;
    description "Indiana 68: ped-overlap clearance began.";
  }
  identity ped-overlap-begin-solid-dont-walk {
    base sc-pedestrian-event-kind;
    description "Indiana 69: ped-overlap solid DONT-WALK began.";
  }
  identity ped-overlap-dark {
    base sc-pedestrian-event-kind;
    description "Indiana 70: ped-overlap dark.";
  }
  identity ped-detector-off {
    base sc-pedestrian-event-kind;
    description "Indiana 89: ped detector off.";
  }
  identity ped-detector-on {
    base sc-pedestrian-event-kind;
    description "Indiana 90: ped detector on.";
  }
  identity ped-detector-failed {
    base sc-pedestrian-event-kind;
    description "Indiana 91: ped detector failed.";
  }
  identity ped-detector-restored {
    base sc-pedestrian-event-kind;
    description "Indiana 92: ped detector restored.";
  }

  /* --------------------------------------------------------------
   * Detector events (Indiana codes 81-88)
   * -------------------------------------------------------------- */

  identity vehicle-detector-off {
    base sc-detector-event-kind;
    description "Indiana 81: vehicle detector off (call drop).";
  }
  identity vehicle-detector-on {
    base sc-detector-event-kind;
    description "Indiana 82: vehicle detector on (call placed).";
  }
  identity vehicle-detector-restored {
    base sc-detector-event-kind;
    description "Indiana 83: vehicle detector restored from fault.";
  }
  identity vehicle-detector-fault-other {
    base sc-detector-event-kind;
    description "Indiana 84: vehicle detector fault (unspecified).";
  }
  identity vehicle-detector-fault-watchdog {
    base sc-detector-event-kind;
    description "Indiana 85: vehicle detector watchdog fault.";
  }
  identity vehicle-detector-fault-open-loop {
    base sc-detector-event-kind;
    description "Indiana 86: vehicle detector open-loop fault.";
  }
  identity vehicle-detector-fault-shorted-loop {
    base sc-detector-event-kind;
    description "Indiana 87: vehicle detector shorted-loop fault.";
  }
  identity vehicle-detector-fault-excessive-change {
    base sc-detector-event-kind;
    description "Indiana 88: vehicle detector excessive-change fault.";
  }

  /* --------------------------------------------------------------
   * Overlap events (Indiana codes 61-66)
   * -------------------------------------------------------------- */

  identity overlap-begin-green {
    base sc-overlap-event-kind;
    description "Indiana 61: overlap began green.";
  }
  identity overlap-begin-trailing-green-extension {
    base sc-overlap-event-kind;
    description "Indiana 62: overlap began trailing-green extension.";
  }
  identity overlap-begin-yellow {
    base sc-overlap-event-kind;
    description "Indiana 63: overlap began yellow.";
  }
  identity overlap-begin-red-clearance {
    base sc-overlap-event-kind;
    description "Indiana 64: overlap began red-clearance.";
  }
  identity overlap-off {
    base sc-overlap-event-kind;
    description "Indiana 65: overlap off (inactive with red indication).";
  }
  identity overlap-dark {
    base sc-overlap-event-kind;
    description "Indiana 66: overlap dark.";
  }

  /* --------------------------------------------------------------
   * Preemption events (Indiana codes 101-111, 116)
   * -------------------------------------------------------------- */

  identity preempt-advance-warning {
    base sc-preemption-event-kind;
    description "Indiana 101: preempt advance-warning input.";
  }
  identity preempt-call-on {
    base sc-preemption-event-kind;
    description "Indiana 102: preempt call input on.";
  }
  identity preempt-gate-down {
    base sc-preemption-event-kind;
    description "Indiana 103: preempt gate-down input received.";
  }
  identity preempt-call-off {
    base sc-preemption-event-kind;
    description "Indiana 104: preempt call input off.";
  }
  identity preempt-entry-started {
    base sc-preemption-event-kind;
    description "Indiana 105: preempt entry interval started.";
  }
  identity preempt-track-clearance {
    base sc-preemption-event-kind;
    description "Indiana 106: preempt track-clearance interval began.";
  }
  identity preempt-dwell-service {
    base sc-preemption-event-kind;
    description "Indiana 107: preempt dwell-service interval began.";
  }
  identity preempt-link-active-on {
    base sc-preemption-event-kind;
    description "Indiana 108: preempt link-active on.";
  }
  identity preempt-link-active-off {
    base sc-preemption-event-kind;
    description "Indiana 109: preempt link-active off.";
  }
  identity preempt-max-presence-exceeded {
    base sc-preemption-event-kind;
    description "Indiana 110: preempt max-presence exceeded.";
  }
  identity preempt-exit-interval {
    base sc-preemption-event-kind;
    description "Indiana 111: preempt exit-interval began.";
  }
  identity preempt-force-off-phase {
    base sc-preemption-event-kind;
    description "Indiana 116: preempt force-off applied to phase.";
  }

  /* --------------------------------------------------------------
   * TSP events (Indiana codes 19, 93-94, 112-115, 117-119)
   * -------------------------------------------------------------- */

  identity tsp-early-force-off-phase {
    base sc-tsp-event-kind;
    description "Indiana 19: TSP early force-off applied to phase.";
  }
  identity tsp-detector-off {
    base sc-tsp-event-kind;
    description "Indiana 93: TSP detector off.";
  }
  identity tsp-detector-on {
    base sc-tsp-event-kind;
    description "Indiana 94: TSP detector on.";
  }
  identity tsp-check-in {
    base sc-tsp-event-kind;
    description "Indiana 112: TSP check-in.";
  }
  identity tsp-adjustment-early-green {
    base sc-tsp-event-kind;
    description "Indiana 113: TSP adjustment to early-green.";
  }
  identity tsp-adjustment-extend-green {
    base sc-tsp-event-kind;
    description "Indiana 114: TSP adjustment to extend-green.";
  }
  identity tsp-check-out {
    base sc-tsp-event-kind;
    description "Indiana 115: TSP check-out.";
  }
  identity tsp-early-force-off-cycle {
    base sc-tsp-event-kind;
    description "Indiana 117: TSP early force-off applied to cycle.";
  }
  identity tsp-service-start {
    base sc-tsp-event-kind;
    description "Indiana 118: TSP service-start.";
  }
  identity tsp-service-end {
    base sc-tsp-event-kind;
    description "Indiana 119: TSP service-end.";
  }
  identity tsp-request-denied {
    base sc-tsp-event-kind;
    description
      "TSP priority request was rejected by the Priority Request
       Server (e.g. reservice lock, coordination constraint, a
       higher-priority conflicting request, or PRS disabled). Pairs
       with the tsp-event denial-reason leaf.";
    reference "NTCIP 1211 (Priority Request Server rejected outcome).";
  }
  identity tsp-request-aborted {
    base sc-tsp-event-kind;
    description
      "A previously granted TSP priority service was aborted before
       normal completion (e.g. vehicle left detection range, request
       withdrawn, service superseded).";
    reference "NTCIP 1211 (Priority Request Server aborted outcome).";
  }

  /* --------------------------------------------------------------
   * Coordination events (Indiana codes 50-54, 131-151)
   * -------------------------------------------------------------- */

  identity coord-max-1-in-effect {
    base sc-coordination-event-kind;
    description "Indiana 50: MAX-1 phase-max-in-effect.";
  }
  identity coord-max-2-in-effect {
    base sc-coordination-event-kind;
    description "Indiana 51: MAX-2 phase-max-in-effect.";
  }
  identity coord-dynamic-max-in-effect {
    base sc-coordination-event-kind;
    description "Indiana 52: dynamic-MAX in effect.";
  }
  identity coord-dynamic-max-step-up {
    base sc-coordination-event-kind;
    description "Indiana 53: dynamic-MAX stepped up.";
  }
  identity coord-dynamic-max-step-down {
    base sc-coordination-event-kind;
    description "Indiana 54: dynamic-MAX stepped down.";
  }
  identity coord-pattern-change {
    base sc-coordination-event-kind;
    description "Indiana 131: coordination pattern changed.";
  }
  identity coord-cycle-length-change {
    base sc-coordination-event-kind;
    description "Indiana 132: cycle-length changed.";
  }
  identity coord-offset-change {
    base sc-coordination-event-kind;
    description "Indiana 133: offset changed.";
  }
  identity coord-programmed-split-change {
    base sc-coordination-event-kind;
    description
      "Indiana 134-149: programmed split for phase 1..16 changed.
       The specific phase is carried in the notification's payload
       (split-number leaf), not in the identityref.";
  }
  identity coord-cycle-state-change {
    base sc-coordination-event-kind;
    description
      "Indiana 150: coordination cycle-state change. The controller's
       coordination cycle-state value is carried in the notification
       payload, not the identityref: 0=Free, 1=In Step,
       2=Transition-Add, 3=Transition-Subtract, 4=Transition-Dwell,
       5=Local Zero, 6=Begin Pickup, 7=Master Cycle Zero (added in the
       2020 revision — logged when the master controller clock turns
       zero).";
  }
  identity phase-barrier-termination {
    base sc-phase-event-kind;
    description "Indiana 31: the active phase pair terminated and the controller crossed the barrier.";
    reference "ATSPM Indiana enumeration code 31 (barrier termination).";
  }

  identity overlap-fya-begin-permissive {
    base sc-overlap-event-kind;
    description
      "Indiana 32: a flashing-yellow-arrow overlap began its permissive
       (flashing yellow) interval. Required to separate permissive from
       protected left-turn service in FYA performance measures.";
    reference "ATSPM Indiana enumeration code 32 (FYA begin permissive).";
  }
  identity overlap-fya-end-permissive {
    base sc-overlap-event-kind;
    description "Indiana 33: a flashing-yellow-arrow overlap ended its permissive interval.";
    reference "ATSPM Indiana enumeration code 33 (FYA end permissive).";
  }

  identity controller-clock-updated {
    base sc-comm-health-event-kind;
    description
      "Indiana 181: the controller's clock was set or stepped. Every
       duration-based performance measure is computed from HR timestamps,
       so a clock step invalidates measures spanning it -- a consumer
       that cannot see this event silently reports corrupted durations.";
    reference "ATSPM Indiana enumeration code 181 (clock updated).";
  }

  identity coord-yield-point {
    base sc-coordination-event-kind;
    description
      "Indiana 151: coordinated-phase yield point — set once per
       cycle for each coordinated phase, when the controller suspends
       the coordinated phase.";
  }

  /* --------------------------------------------------------------
   * Fault events (Indiana codes 173-185, currently mapped)
   * -------------------------------------------------------------- */

  identity fault-unit-flash-status {
    base controller-fault-event-kind;
    description "Indiana 173: unit flash-status change.";
  }
  identity fault-unit-alarm-group-1 {
    base controller-fault-event-kind;
    description "Indiana 174: unit alarm group 1 state change.";
  }
  identity fault-power-failure {
    base controller-fault-event-kind;
    description "Indiana 182/184: power failure / power restored.";
  }
  identity fault-vendor-alarm {
    base controller-fault-event-kind;
    description
      "Indiana 185: vendor-specific alarm raised. Vendor modules MAY
       derive more specific identities from this for their own
       vendor-alarm-N codes.";
  }

  identity controller-fault-event-kind {
    base sc-fault-event-kind;
    description
      "High-resolution controller fault event from indianamap codes
       173-185. Used by the controller-fault-event notification
       (openits-signal-control-events) to discriminate this HR
       fault class from cabinet-level faults emitted via fault-raised.";
  }

  /* --------------------------------------------------------------
   * Fault categories (state-tree active-fault list)
   *
   * Coarse fault classes for the config-false 'faults' list in
   * openits-signal-control. Parallel to the per-service fault-category
   * identities in the other -types modules (dms-fault-*, ess-fault-*,
   * ramp-meter-fault-*). Basing them on sc-fault-event-kind — which
   * dual-bases onto openits-types:fault-event-kind — makes a
   * signal-controller cabinet fault filterable fleet-wide via
   * derived-from-or-self(fault-event-kind).
   * -------------------------------------------------------------- */

  identity sc-fault-detector {
    base sc-fault-event-kind;
    description "Vehicle/pedestrian detector fault (watchdog, open/shorted loop, etc.).";
  }
  identity sc-fault-lamp {
    base sc-fault-event-kind;
    description "Signal-head lamp/LED load fault (out, dim, or erratic).";
  }
  identity sc-fault-conflict {
    base sc-fault-event-kind;
    description "Conflict-monitor / MMU fault (conflicting indications, forced flash).";
  }
  identity sc-fault-communication {
    base sc-fault-event-kind;
    description "Controller communication fault (link down, polling timeout).";
  }
  identity sc-fault-power {
    base sc-fault-event-kind;
    description "Cabinet power fault (loss, brownout, UPS-on-battery).";
  }
  identity sc-fault-cabinet {
    base sc-fault-event-kind;
    description "Cabinet-environment or hardware fault (door, temperature, fan).";
  }
  identity sc-fault-software {
    base sc-fault-event-kind;
    description "Controller software/firmware fault (watchdog reset, database error).";
  }

  /* --------------------------------------------------------------
   * External I/O events (Indiana codes 178, 180)
   * -------------------------------------------------------------- */

  identity ext-io-manual-control-enable {
    base sc-external-io-event-kind;
    description
      "Indiana 178: manual control enable on/off — the controller's
       manual-control input was engaged or released. (In NEMA
       TS2-family cabinet hardware this input is commonly wired to
       the front-panel switch colloquially called the 'police panel',
       though that equivalence is a cabinet-hardware convention, not
       something the Indiana enumeration document itself states.) The
       on/off state is carried in the notification payload, not the
       identityref.";
  }
  identity ext-io-stop-time-input {
    base sc-external-io-event-kind;
    description
      "Indiana 180: stop-time input on/off. Set when a stop-time
       input is applied to or removed from the controller, regardless
       of the source or state of the stop. The on/off state is
       carried in the notification payload, not the identityref.";
  }

  /* --------------------------------------------------------------
   * Notification-kind identities ('kind' identityref targets for
   * notifications outside the Indiana enumeration proper: periodic
   * reports and discrete coordination/status events)
   * -------------------------------------------------------------- */

  identity vehicle-detector-fault-no-activity {
    base sc-detector-event-kind;
    base sc-fault-detector;
    description
      "The detector reported no actuation for longer than its configured
       no-activity interval. The controller diagnoses this itself from
       detectors/detector/config/no-activity-minutes; it is the most
       common detector work order and previously had no identity, so it
       could only be raised as the coarse sc-fault-detector.";
    reference "NTCIP 1202:2019 §5 (vehicleDetectorReportedAlarms noActivity).";
  }
  identity vehicle-detector-fault-max-presence {
    base sc-detector-event-kind;
    base sc-fault-detector;
    description
      "The detector held a continuous call for longer than its configured
       maximum-presence interval -- the classic stuck-on loop.";
    reference "NTCIP 1202:2019 §5 (vehicleDetectorReportedAlarms maxPresence).";
  }
  identity vehicle-detector-fault-erratic-count {
    base sc-detector-event-kind;
    base sc-fault-detector;
    description
      "The detector's actuation rate exceeded its configured erratic-count
       threshold, indicating electrical noise or a failing card rather
       than traffic.";
    reference "NTCIP 1202:2019 §5 (vehicleDetectorReportedAlarms erraticCounts).";
  }
  identity vehicle-detector-fault-communications {
    base sc-detector-event-kind;
    base sc-fault-detector;
    description
      "The controller lost communication with the detector card or rack,
       so the channel's state is unknown rather than known-idle.";
    reference "NTCIP 1202:2019 §5 (vehicleDetectorReportedAlarms).";
  }

  identity sc-detector-report {
    base sc-detector-event-kind;
    base openits-types:report-event-kind;
    description "Periodic per-detector interval report.";
  }
  identity sc-plan-applied {
    base sc-coordination-event-kind;
    description
      "A coordination plan was applied (discrete coordination event —
       NOT a periodic report, so no report-event-kind base).";
  }
  identity sc-operational-status-report {
    base signal-control-event-kind;
    base openits-types:report-event-kind;
    description "Periodic controller status report.";
  }

  /* --------------------------------------------------------------
   * Signal-control typedefs
   *
   * Shared across the service core (openits-signal-control) and the
   * notification companion (openits-signal-control-events). Living
   * here lets the notification companion import only this -types
   * module rather than the full service core.
   * -------------------------------------------------------------- */

  identity preemption-type {
    description
      "Class of active preemption. Preemption overrides normal operation
       (contrast priority-type, which only biases it). An identity, not a
       closed enum, so a vendor/agency can derive a new preemption source
       (drawbridge, emergency-gate) without a core change.";
    reference "NTCIP 1202 v03 (preemption); MUTCD 11th ed. Ch. 8C.";
  }
  identity preempt-railroad          { base preemption-type; description "Railroad / rail-transit grade-crossing preemption."; }
  identity preempt-emergency-vehicle { base preemption-type; description "Emergency-vehicle preemption."; }
  identity preempt-other             { base preemption-type; description "Other vendor/agency preemption source (drawbridge, emergency-gate, etc.)."; }

  identity priority-type {
    description
      "Class of an active TSP priority request. Priority biases the phase
       sequence without overriding it (as opposed to preemption -- see
       preemption-type), and is a separate axis from it so an active rail
       preemption and an active transit priority request are separately
       representable.

       An identity, matching preemption-type beside it: agencies grant
       priority to vehicle classes the core has not catalogued (school
       buses, snow plows, refuse fleets on a winter schedule), and a
       vendor or agency module derives one without a core revision. The
       former enum's 'none' member is gone: absence of a request is
       absence of the leaf, not a value.";
    reference "NTCIP 1211 (priority-class / PRS request semantics).";
  }
  identity priority-transit {
    base priority-type;
    description "Transit vehicle priority -- the NTCIP 1211 base case.";
  }
  identity priority-freight {
    base priority-type;
    description "Freight / commercial-vehicle priority, typically on a designated truck route.";
  }
  identity priority-emergency {
    base priority-type;
    description
      "Emergency-vehicle priority: a request that biases the sequence
       without seizing it. Distinct from preempt-emergency-vehicle,
       which overrides the sequence outright.";
  }
  identity priority-other {
    base priority-type;
    description "A priority class not otherwise catalogued; the slot an agency derives from.";
  }

  typedef detector-channel {
    type uint16 { range "1..65535"; }
    description "Controller-local detector channel number. Shared by the core detector list key and the detector/pedestrian event surfaces.";
    reference "NTCIP 1202:2019 §5 (vehicleDetectorTable).";
  }
  typedef preempt-slot {
    type uint8 { range "1..255"; }
    description "Preemptor slot / preempt-number (1-based). Shared by the core preemptor list key and the preemption event surfaces.";
    reference "NTCIP 1202:2019 §5 (preemption).";
  }
  typedef plan-id {
    type uint8 { range "1..255"; }
    description
      "1-based library identifier in the NTCIP 1..255 index space:
       coordination timing-plan / pattern number, and reused for other
       same-shaped library keys (the phase-sequence library's
       sequence-id). Shared by the core coordination + sequence
       libraries and the plan-applied event.";
    reference "NTCIP 1202:2019 §5 (coordTable / patternTable / sequenceTable).";
  }
  typedef overlap-number {
    type uint8 { range "1..255"; }
    description "Overlap number (1-based), matching NTCIP overlapTable numeric indexing. Shared by the core overlap list key and the overlap-change event.";
    reference "NTCIP 1202:2019 §5 (overlapTable).";
  }

  typedef tsam-engagement-state {
    type enumeration {
      enum disabled  { value 1; }
      enum advisory  { value 2; }
      enum active    { value 3; }
      enum suspended { value 4; }
    }
    description "TSAM (adaptive management) engagement state. Shared by the tsam-mode-changed notification's prior/current leaves.";
  }

  identity controller-mode {
    base openits-types:operational-mode;
    description
      "Top-level operational mode of a signal controller. An identity
       (not a closed enum) so a vendor can derive a proprietary mode
       from this base without a core change; the standard modes below
       cover NTCIP 1202 v03.";
    reference "NTCIP 1202 v03 (controller operating modes).";
  }
  identity mode-coordinated { base controller-mode; description "Coordinated operation under a timing plan."; }
  identity mode-free {
    base controller-mode;
    description
      "Free (uncoordinated) actuated operation. This is the single
       uncoordinated-actuated mode: NTCIP and signal technicians treat 'normal'
       and 'free' as one operating mode, so the former mode-normal identity is
       collapsed into this one. A coordinated controller that is not yet in step
       is reported via coordination/state/cycle-state, not a distinct mode.";
  }
  identity mode-flash       {
    base controller-mode;
    description
      "Flashing operation (e.g. MMU-forced or programmed flash). A single
       mode value covers all flash — it does not split by cause. The
       cause is carried on two other surfaces instead: the config-false
       state tree's flash-cause leaf (current cause, state) and
       mode-changed's trigger leaf (cause of this specific mode
       transition); consumers read whichever surface fits their need
       without the mode taxonomy itself splitting.";
  }
  identity mode-preempt     { base controller-mode; description "Preemption is active (rail / emergency)."; }
  identity mode-priority    { base controller-mode; description "Transit/freight priority is active."; }
  identity mode-manual      { base controller-mode; description "Manual control (operator or cabinet switch)."; }
  identity mode-off         { base controller-mode; description "Controller off / dark."; }

  /* --------------------------------------------------------------
   * Flash cause + MMU fault type
   *
   * mode-flash (above) says only *that* the controller is flashing.
   * These identity sets say *why*: flash-cause backs the config-false
   * state tree's flash-cause leaf and the optional flash-cause on
   * controller-fault-event (openits-signal-control-events);
   * monitor-fault-type backs the state tree's monitor/fault-type leaf.
   * Indiana 173 (fault-unit-flash-status) is the HR-log wire source for
   * the flash cause, and NTCIP unitFlashStatus is the polled one; NEMA
   * TS2 section 4 defines the monitored fault classes that force a
   * cabinet into flash, which a TS1 conflict monitor and an
   * ITS-cabinet CMU monitor equally.
   * -------------------------------------------------------------- */

  identity coordination-cycle-state {
    description
      "Coordination cycle state. An identity, not an enum: transition
       method is vendor territory -- shortway and adaptive transitions
       ship today beyond the classic add/subtract/dwell set -- and
       controller-mode beside it is already an identity for the same
       reason.

       Two altitudes, so the type does the work a prose caveat used to.
       cycle-state-persistent below covers the states a poller can
       sample; the three instantaneous markers derive from this root
       directly, because they are transitions an event reports and are
       meaningless as a sampled value. The polled readback in
       openits-signal-control narrows to the persistent base and
       therefore cannot carry a marker; the coordination-change
       notification takes the full axis.";
    reference "ATSPM Indiana enumeration code 150 (coord cycle state).";
  }

  identity cycle-state-persistent {
    base coordination-cycle-state;
    description
      "A coordination state that persists long enough for a poller to
       sample it, as against an instantaneous HR-log marker.";
  }
  identity cycle-free                { base cycle-state-persistent; description "Not coordinated."; }
  identity cycle-in-step             { base cycle-state-persistent; description "Coordinated and in step with the master cycle."; }
  identity cycle-transition-add      { base cycle-state-persistent; description "Transitioning by adding time to the cycle."; }
  identity cycle-transition-subtract { base cycle-state-persistent; description "Transitioning by subtracting time from the cycle."; }
  identity cycle-transition-dwell    { base cycle-state-persistent; description "Transitioning by dwelling in the coordinated phase."; }

  identity cycle-local-zero        { base coordination-cycle-state; description "Local cycle zero point reached (instantaneous HR marker)."; }
  identity cycle-begin-pickup      { base coordination-cycle-state; description "Coordination pickup began (instantaneous HR marker)."; }
  identity cycle-master-cycle-zero { base coordination-cycle-state; description "Master cycle zero point reached (instantaneous HR marker)."; }

  identity flash-cause {
    description
      "Why the controller is currently in flashing operation.";
    reference "NEMA TS2-2021 section 4; Indiana 173 (fault-unit-flash-status).";
  }
  identity flash-mmu-conflict {
    base flash-cause;
    description
      "Flash forced by the cabinet's signal monitor: its flash input to
       the controller is active. Maps to NTCIP unitFlashStatus mmu(6)
       (renamed smu(6), Signal Monitoring Unit, in NTCIP 1202 v04).

       Covers every cabinet monitor — a TS2 Malfunction Management
       Unit, a TS1 conflict monitor, or an ITS-cabinet CMU — and every
       monitored condition that trips it, not only a conflict: red-fail,
       dual indication, clearance, CVM, +24V, field check and the rest.
       The specific condition is reported separately as a
       monitor-fault-type. The identity name predates this definition;
       it does not mean the cause was a conflict.";
    reference "NEMA TS2-2021 section 4; NTCIP 1202:2019 §5 (unitFlashStatus mmu(6)); NTCIP 1202 v04 (unitFlashStatus smu(6)).";
  }
  identity flash-fault-monitor {
    base flash-cause;
    description
      "Flash the controller unit initiated itself because it detected
       a fault of its own, with the cabinet monitor's flash input not
       the cause. Maps to NTCIP unitFlashStatus faultMonitor(5)
       (renamed controllerFaultFlash(5) in NTCIP 1202 v04).

       Not a cabinet-monitor flash: a flash forced by any cabinet
       monitor, including a TS1 conflict monitor or an ITS-cabinet CMU,
       is flash-mmu-conflict. The identity name predates this
       definition.";
    reference "NTCIP 1202:2019 §5 (unitFlashStatus faultMonitor(5)); NTCIP 1202 v04 (unitFlashStatus controllerFaultFlash(5)).";
  }
  identity flash-automatic {
    base flash-cause;
    description
      "Flash entered automatically by controller logic for a cause
       other than a specific monitor fault class (e.g. an internal
       controller malfunction detected outside the monitor). Maps to
       NTCIP unitFlashStatus automatic(3) where the controller does not
       report a more specific cause.";
    reference "Indiana 173 (fault-unit-flash-status); NTCIP 1202:2019 §5 (unitFlashStatus).";
  }
  identity flash-programmed-tod {
    base flash-cause;
    description
      "Scheduled time-of-day flash: a normal, non-fault operating
       state programmed into the controller's timing plan (e.g.
       overnight flash), not a monitor-forced condition. An OpenITS
       refinement of NTCIP unitFlashStatus automatic(3) for the case
       where the schedule is the known source; a controller that
       reports automatic flash without naming the schedule as its
       source is reported as flash-automatic.";
    reference "Indiana 173 (fault-unit-flash-status).";
  }
  identity flash-other {
    base flash-cause;
    description
      "Flash for a cause the controller reports but does not classify.
       Maps to NTCIP unitFlashStatus other(1); present so a decoder
       never has to invent a more specific cause than the wire gave it.";
    reference "NTCIP 1202:2019 §5 (unitFlashStatus).";
  }
  identity flash-manual {
    base flash-cause;
    description
      "Flash commanded by an operator, via the cabinet flash switch
       or another manual-control input.";
    reference "Indiana 173 (fault-unit-flash-status).";
  }
  identity flash-startup {
    base flash-cause;
    description
      "Flash entered during controller power-up / start-up delay,
       before normal operation begins.";
    reference "NEMA TS2-2021 section 4; Indiana 173 (fault-unit-flash-status).";
  }
  identity flash-preempt {
    base flash-cause;
    description
      "Flash entered as the commanded response to an active
       preemption input.";
    reference "Indiana 173 (fault-unit-flash-status).";
  }
  identity monitor-fault-type {
    base sc-fault-event-kind;
    description
      "Cabinet monitor fault classification — the specific monitored
       condition that forced (or would force) the cabinet into flash.

       Named for the FUNCTION, not for one cabinet family's hardware: a
       TS2 Malfunction Management Unit, a TS1 conflict monitor and an
       ITS-cabinet CMU all monitor red-fail, dual-indication, conflict
       and clearance, and all three report them here. Which unit is
       fitted is a cabinet property, not a property of the fault.

       Derives from sc-fault-event-kind, so every monitor-* value is also
       a signal-control fault kind: fault-raised and faults/fault can carry
       the specific monitored condition (a red-fail as itself, not as
       sc-fault-conflict).";
    reference "NEMA TS2-2021 section 4; NEMA TS1 section 6; ATC Cabinet Standard (CMU).";
  }
  identity monitor-red-fail {
    base monitor-fault-type;
    description
      "Red-fail monitor: no indication at all (no green, yellow or red)
       was detected on a monitored channel that should be showing one,
       so the head may be dark. Not a conflict between channels; that
       is monitor-conflict.";
    reference "NEMA TS2-2021 section 4.";
  }
  identity monitor-dual-indication {
    base monitor-fault-type;
    description
      "Dual-indication monitor: two or more of green, yellow and red
       were detected active at the same time on one monitored
       channel.";
    reference "NEMA TS2-2021 section 4.";
  }
  identity monitor-conflict {
    base monitor-fault-type;
    description
      "Conflict monitor: non-compatible signal indications were
       detected between two or more channels per the monitor's
       programmed channel-compatibility matrix.";
    reference "NEMA TS2-2021 section 4.";
  }
  identity monitor-clearance {
    base monitor-fault-type;
    description
      "Minimum clearance monitor: a monitored channel's yellow-change
       or red-clearance interval was shorter than the monitor's
       programmed minimum.";
    reference "NEMA TS2-2021 section 4.";
  }
  identity monitor-cvm {
    base monitor-fault-type;
    description
      "Controller Voltage Monitor (CVM) fault: the controller unit's
       CVM health output de-asserted, signalling internal controller
       failure. Distinct from the +24V supply monitor (monitor-24v):
       CVM watches the CONTROLLER, the 24V inputs watch the cabinet
       logic supply — a technician troubleshoots different hardware for
       each.";
    reference "NEMA TS2-2021 section 4.";
  }
  identity monitor-24v {
    base monitor-fault-type;
    description
      "+24V Monitor fault: the cabinet's +24VDC logic supply fell
       outside the monitor's range (24V Monitor I/II inputs). Distinct
       from monitor-cvm, which is the controller unit's own health
       output.";
    reference "NEMA TS2-2021 section 4.";
  }
  identity monitor-field-check {
    base monitor-fault-type;
    description
      "Field-check monitor: the load-switch output a monitored channel
       actually drove did not match the input the controller commanded,
       so the cabinet cannot vouch for what the head is displaying.";
    reference "NEMA TS2-2021 section 4.";
  }
  identity monitor-port1-fail {
    base monitor-fault-type;
    description
      "Port 1 / SDLC communications fault: the monitor lost its serial
       link to the controller unit, so it can no longer compare
       commanded state against field state.";
    reference "NEMA TS2-2021 section 4.";
  }
  identity monitor-diagnostic {
    base monitor-fault-type;
    description
      "The monitor's own internal diagnostic failed — the monitor is
       reporting itself unfit, which is distinct from any signal
       condition it watches.";
    reference "NEMA TS2-2021 section 4.";
  }
  identity monitor-watchdog {
    base monitor-fault-type;
    description
      "Watchdog fault: the controller stopped toggling the watchdog
       output the monitor expects, so the monitor treats the controller
       as hung. Reported by ITS-cabinet CMUs.";
    reference "ATC Cabinet Standard (CMU watchdog).";
  }

  /* --------------------------------------------------------------
   * Detector technology (identity, not enum)
   *
   * Detection technology is a vendor-extensible axis (lidar, thermal,
   * BSM-derived detection all post-date NTCIP 1202's fixed list), so it
   * is an identity: a vendor module derives a new technology without a
   * core revision. Contrast the closed physical sets that stay enums
   * (interval-type, lcs-indication) — see the identity-vs-enum policy in
   * docs/reference/yang-reference-conventions.md.
   * -------------------------------------------------------------- */

  identity detector-type {
    description
      "Detector technology class. Base for the standard NTCIP 1202
       vehicleDetectorTable technologies below; vendors derive
       proprietary or newer technologies (lidar, thermal, BSM-derived)
       from this base.";
    reference "NTCIP 1202:2019 §5 (vehicleDetectorTable).";
  }
  identity detector-inductive-loop {
    base detector-type;
    description "Inductive-loop vehicle detector.";
  }
  identity detector-video {
    base detector-type;
    description "Video image vehicle detector.";
  }
  identity detector-radar {
    base detector-type;
    description "Radar / microwave vehicle detector.";
  }
  identity detector-magnetometer {
    base detector-type;
    description "Magnetometer vehicle detector.";
  }
  identity detector-ped-pushbutton {
    base detector-type;
    description "Pedestrian push-button (actuated) detector.";
  }
  identity detector-ped-passive {
    base detector-type;
    description "Passive pedestrian-presence detector.";
  }
  identity detector-bicycle {
    base detector-type;
    description "Bicycle detector.";
  }
  identity detector-emergency-vehicle {
    base detector-type;
    description "Emergency-vehicle preemption detector.";
  }
  identity detector-transit {
    base detector-type;
    description "Transit-priority detector.";
  }

  /* --------------------------------------------------------------
   * Overlap behavior (identity — extensible: FYA variants, bicycle
   * overlaps, and vendor overlap modes are active extension pressure).
   * -------------------------------------------------------------- */

  identity overlap-type {
    description
      "Overlap behavior class. An identity (not a closed enum) so
       vendors or future standards can derive a new overlap arrangement
       (FYA 3-/4-section, bicycle overlaps) without a core revision.";
    reference "NTCIP 1202:2019 §5 (overlapTable overlapType).";
  }
  identity overlap-normal          { base overlap-type; description "Standard overlap: green while any included phase is green."; }
  identity overlap-pedestrian      { base overlap-type; description "Pedestrian overlap."; }
  identity overlap-fya             { base overlap-type; description "Flashing-yellow-arrow protected/permissive left-turn overlap."; }
  identity overlap-right-turn-arrow { base overlap-type; description "Right-turn arrow overlap."; }
  identity overlap-minus-green {
    base overlap-type;
    description
      "Minus-green overlap: the overlap is SUPPRESSED (not extended) while any
       of its modifier phases are green (NTCIP minusGreenYellow). The modifier
       phases are named by the overlap's modifier-phases leaf-list.";
    reference "NTCIP 1202:2019 §5 (overlapType minusGreenYellow).";
  }

  /* --------------------------------------------------------------
   * Load-switch channel movement (identity — bicycle signal faces are
   * newly standardized; the set is moving).
   * -------------------------------------------------------------- */

  identity channel-movement {
    description
      "Signal movement a load-switch channel drives. An identity so a
       newer movement (e.g. bicycle) can be added without a core change.";
    reference "NTCIP 1202:2019 §5 (channelTable).";
  }
  identity channel-vehicle    { base channel-movement; description "Vehicle signal head."; }
  identity channel-pedestrian { base channel-movement; description "Pedestrian signal head."; }

  /* --------------------------------------------------------------
   * Clock time source (identity — vendor-extensible: PTP and newer
   * GNSS variants post-date the NTCIP 1201 list).
   * -------------------------------------------------------------- */

}
