module openits-dms-events {
  yang-version 1.1;
  namespace "urn:openits:yang:dms-events";
  prefix openits-dms-events;

  import openits-types {
    prefix openits-types;
  }

  import openits-dms-types {
    prefix openits-dms-types;
  }

  organization
    "OpenITS Working Group (proposal)";

  contact
    "OpenITS Working Group (proposal)";

  description
    "Notifications for openits-dms.  Split into a companion module
     so ygot's proto backend can generate protobuf from the base
     module (ygot's proto generator fails on modules containing
     notification statements).";

  openits-types:openits-version "0.5.0";

  revision 2026-07-23 {
    description
      "Add wire-source provenance to message-activation-failed: this event
       is decoded from the sign's own reported NTCIP 1203 dmsMultiSyntaxError
       / dmsMultiSyntaxErrorPosition diagnostic objects, so it carries the
       shared wire-source grouping per the selective provenance policy
       (present iff decoded from a wire).";
    reference "NTCIP 1203 v03.";
  }
  revision 2026-07-21 {
    description
      "attempted-slot-number range 1..65535 (drift fix). Fix a stray '; '
       in a prior revision reference string. Add explicit enum ordinals to
       message-activation-failed error-type.
       - Collapse duplicate same-date revision statements.";
    reference "NTCIP 1203 v03.";
  }
  revision 2026-07-16 {
    description
      "message-activation-failed: add a structured error-type (MULTI syntax
       / unsupported-tag / font-not-found / graphic-not-found / too-long /
       hardware / other) and a MULTI error-position (character offset) so an
       operator can locate and classify the fault without parsing the
       free-form reason (NTCIP 1203 dmsMultiSyntaxError /
       dmsMultiSyntaxErrorPosition). The sign id was already present via the
       event-header. Additive (Cut 3a).";
    reference "NTCIP 1203 v03.";
  }
  revision 2026-07-14 {
    description
      "Cut 3c (events layering): reference message-memory-type via
       openits-dms-types and drop the openits-dms core import — the
       events module now imports only -types (+ shared).
       Wire-neutral.";
  }
  revision 2026-07-13 {
    description
      "Adopt the unified event contract on message-activation-failed:
       the notification now 'uses openits-types:event-header'
       (source-device-id, occurred-at, sequence) and carries a
       mandatory 'kind' identityref under
       openits-dms-types:dms-event-kind
       (openits-dms-types:dms-message-activation-failed). Not a
       periodic report, so no dual report-event-kind base. All
       existing payload leaves (attempted-memory-type,
       attempted-slot-number, reason) are unchanged; the header's
       source-device-id now supplies sign identity. Breaking, pre-v1:
       the notification gains mandatory device identity + sequence.

      Stamp openits-version (borrowed from OpenConfig's
       openconfig-version practice) so tooling can read a
       compatibility-intent signal independent of the revision date.";
    reference "RFC 7950 section 11.";
  }
  revision 2026-07-12 {
    description
      "Rename this module (file, module name, namespace, prefix) from
       the legacy notifications-suffixed name to openits-dms-events: standardize every service notification module on the
       events-suffixed name. Mechanical rename only — no notification
       content changed; ce-types (service-derived, not module-derived)
       and proto are unaffected. Repoint sign-fault-raised's
       'category' base from the deleted gen-1
       openits-dms:fault-category to
       openits-dms-types:dms-fault-event-kind — breaking, since
       identity names change, but wire-neutral since the wire
       representation of an identityref is a string (pre-v1,
       acceptable). Delete the deprecated per-service fault/mode
       shims (sign-fault-raised, sign-fault-cleared,
       sign-mode-changed), superseded by
       openits-common-fault-events:{fault-raised,fault-cleared} and
       openits-common-mode-events:mode-changed, discriminated by kind
       derived from openits-dms-types.";
    reference
      "RFC 7950 section 11 (breaking YANG evolution: identity
       rename).";
  }
  revision 2026-07-10 {
    description
      "Replace the inline severity enumeration on sign-fault-raised
       with the shared openits-types:fault-severity typedef. Member
       set and order unchanged — wire-stable.";
  }
  revision 2026-06-12 {
    description
      "Deprecate sign-fault-raised, sign-fault-cleared, and
       sign-mode-changed in favour of the cross-service
       openits-common-fault-events fault-raised/fault-cleared and
       openits-common-mode-events mode-changed notifications, which
       carry a dms-classified kind identityref
       (openits-dms-types:dms-fault-event-kind tree) plus wire-source
       provenance. No emitter ever shipped for the deprecated
       notifications; they remain for the deprecation window only.";
  }
  revision 2026-05-23 {
    description
      "Add the sign-fault-cleared notification as the companion to
       sign-fault-raised. Closes the gap where the CE catalog declared
       openits.dms.sign-fault-cleared.v1 with no YANG schema home.";
  }
  revision 2026-04-19 {
    description "Initial release.";
  }

  /* --------------------------------------------------------------
   * Notifications
   * -------------------------------------------------------------- */

  notification message-activation-failed {
    openits-types:arc-it-flow
      "Roadway Equipment -> TMC : roadway equipment status";
    description
      "An attempt to activate a stored message on the sign failed.
       Lets the TMC distinguish 'command accepted but never displayed'
       from successful activation.";

    leaf kind {
      type identityref {
        base openits-dms-types:dms-event-kind;
      }
      mandatory true;
      description
        "Event classifier; openits-dms-types:dms-message-activation-failed
         for this notification.";
    }
    uses openits-types:event-header;

    leaf attempted-memory-type {
      type openits-dms-types:message-memory-type;
      description "Which memory bank the activation targeted (e.g., changeable, volatile, schedule).";
    }
    leaf attempted-slot-number { type uint16 { range "1..65535"; } description "Slot number within the targeted memory bank."; }
    leaf reason                { type string; description "Sign-reported reason the activation failed (validation, conflict, hardware)."; }
    leaf error-type {
      type enumeration {
        enum syntax            { value 0; description "General MULTI syntax error."; }
        enum unsupported-tag   { value 1; description "A MULTI tag the sign does not support (see sign/state/capabilities/supported-multi-tags)."; }
        enum font-not-found    { value 2; description "A referenced font is not loaded on the sign."; }
        enum graphic-not-found { value 3; description "A referenced graphic is not loaded on the sign."; }
        enum too-long          { value 4; description "The message does not fit the sign face (see capabilities)."; }
        enum hardware          { value 5; description "A hardware fault prevented activation (not a content error)."; }
        enum other             { value 6; description "Failure not otherwise classified."; }
      }
      description
        "Structured classification of the activation failure (NTCIP 1203
         dmsMultiSyntaxError), complementing the free-form reason so a TMC
         can route/aggregate failures without parsing prose. The sign id is
         already carried by the event-header (source-device-id).";
    }
    leaf error-position {
      type uint16;
      description
        "Zero-based character offset in the attempted MULTI string where the
         syntax/tag error was detected (NTCIP 1203 dmsMultiSyntaxErrorPosition),
         so an operator can locate the fault. Absent when the failure is not
         a MULTI-content error (e.g. error-type = hardware).";
    }

    uses openits-types:wire-source;
  }
}
