module openits-traffic-sensor-events {
  yang-version 1.1;
  namespace "urn:openits:yang:traffic-sensor-events";
  prefix openits-ts-events;

  import ietf-yang-types {
    prefix yang;
  }

  import openits-types {
    prefix openits-types;
  }

  import openits-traffic-sensor {
    prefix openits-ts;
  }

  organization
    "OpenITS Working Group (proposal)";

  contact
    "OpenITS Working Group (proposal)";

  description
    "Notifications for openits-traffic-sensor.  Split into a
     companion module so ygot's proto backend can generate protobuf
     from the base module (ygot's proto generator fails on modules
     containing notification statements).";

  openits-types:openits-version "0.1.0";

  revision 2026-07-12 {
    description
      "Rename this module (file, module name, namespace, prefix) from
       the legacy notifications-suffixed name to
       openits-traffic-sensor-events: standardize every
       service notification module on the events-suffixed name.
       Mechanical rename only — no notification content changed;
       ce-types (service-derived, not module-derived) and proto are
       unaffected. Delete the bespoke
       traffic-sensor-fault-raised/cleared notifications;
       traffic-sensor now emits
       openits-common-fault-events:{fault-raised,fault-cleared} with
       kind derived from
       openits-traffic-sensor-types:traffic-sensor-fault-event-kind,
       completing the orphan-service fault consolidation.";
  }
  revision 2026-07-11 {
    description
      "Repoint traffic-sensor-fault-raised's 'category' base from the
       deleted gen-1 openits-ts:fault-category to
       openits-traffic-sensor-types:traffic-sensor-fault-event-kind.
       Breaking: identity names change; wire-neutral since the wire
       representation of an identityref is a string (pre-v1,
       acceptable).";
    reference "RFC 7950 section 11 (breaking YANG evolution: identity rename).";
  }
  revision 2026-07-10 {
    description
      "Replace the inline severity enumeration on
       traffic-sensor-fault-raised with the shared
       openits-types:fault-severity typedef. Member set and order
       unchanged — wire-stable.

       Also, replace the inline latitude/longitude leaves on
       traffic-sensor-status-report with openits-types:geo-point.
       Already fraction-digits 7 — no precision change. Member set
       and field tags unchanged (latitude/longitude keep their
       locked tags).";
  }
  revision 2026-07-07 {
    description "Initial release.";
  }

  /* --------------------------------------------------------------
   * Notifications
   * -------------------------------------------------------------- */

  notification traffic-interval-report {
    openits-types:arc-it-flow
      "ITS Roadway Equipment -> TMC : traffic flow";
    description
      "Periodic per-lane aggregate report, emitted once per
       configured data-interval.  Carries every monitored lane's
       interval data in a single event so consumers see a coherent
       cross-lane snapshot.";

    list lane {
      key "lane-id";
      description "Interval data for one monitored lane.";

      leaf lane-id {
        type uint8 {
          range "1..32";
        }
        description "Sensor-local lane number.";
      }
      leaf name {
        type string;
        description
          "Operator-facing lane label (e.g. the sensor's native lane
           identifier).  Optional; consumers fall back to lane-id.";
      }
      leaf carriageway {
        type string;
        description
          "Carriageway / travel-direction grouping this lane belongs
           to (see openits-traffic-sensor lane/carriageway).";
      }
      uses openits-ts:lane-interval-data;
    }
  }

  notification queue-state-changed {
    openits-types:arc-it-flow
      "ITS Roadway Equipment -> TMC : traffic flow";
    description
      "A queue-detection zone changed state (queue started, cleared,
       or its persisted duration was re-reported).  The
       traffic-sensor/queues container is the digital-twin rollup of
       these events.";

    leaf zone-id {
      type string;
      description "Sensor-local queue-zone identifier.";
    }
    leaf queueing {
      type boolean;
      description "A queue is currently present in the zone.";
    }
    leaf queue-duration-s {
      type uint32;
      units "seconds";
      description
        "How long the current queue has persisted; 0 when not
         queueing.";
    }
    leaf queue-start {
      type yang:date-and-time;
      description
        "Wall-clock time the current queue began; absent when not
         queueing.";
    }
  }

  notification traffic-sensor-status-report {
    openits-types:arc-it-flow
      "ITS Roadway Equipment -> Maintenance : equipment maintenance status";
    description
      "Periodic station health / availability report.  Carries the
       station identity and generic operational status so downstream
       systems can locate the station and trend its availability;
       vendor diagnostics (e.g. camera view quality, frame rate) ride
       as augments on this notification.";

    leaf name {
      type string;
      description "Operator-facing sensor name.";
    }
    uses openits-types:geo-point;
    leaf operational-status {
      type enumeration {
        enum active   { description "The sensor is producing usable data."; }
        enum inactive { description "The sensor is not producing usable data."; }
      }
      description "Whether the sensor is currently producing usable data.";
    }
    leaf inactive-reason {
      type identityref {
        base openits-ts:inactive-reason;
      }
      description
        "Why the sensor is inactive, when operational-status is
         inactive.  Open identity slot; vendors derive concrete
         reasons.  Absent when the sensor is active.";
    }
  }
}
