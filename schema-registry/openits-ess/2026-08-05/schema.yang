module openits-ess {
  yang-version 1.1;
  namespace "urn:openits:yang:ess";
  prefix openits-ess;

  import ietf-yang-types {
    prefix yang;
  }

  import openits-types {
    prefix openits-types;
  }

  import openits-ess-types {
    prefix openits-ess-types;
  }

  organization
    "OpenITS Working Group (proposal)";

  contact
    "OpenITS Working Group (proposal)";

  description
    "YANG data model for Environmental Sensor Stations (ESS) — the
     roadside devices commonly referred to as RWIS (Road Weather
     Information System).

     Transport-independent replacement for NTCIP 1204 v04, aligned
     with ARC-IT 9.1 service package MC01 (Environmental Monitoring
     Station).

     ESS devices are pure-observation: no actuators, no commands, no
     safety-critical timing.  The model therefore has almost no
     `must`-constraints.  Bounded values are enforced via YANG
     `range` (humidity 0..100 %, wind-direction 0..360°, pressure
     300..1100 hPa, etc.) rather than XPath constraints, because the
     bounds are **physical** rather than **operational**.

     Every numeric leaf carries a `units` statement.  Agents that
     report different units MUST convert at the translator boundary;
     the wire format is canonical.

     Copyright (c) 2026.  Distributed under Apache 2.0.";

  openits-types:openits-version "0.5.0";

  revision 2026-08-05 {
    description
      "Model-review remediation (2026-08): append visibility-situation
       members mist-haze, sand-storm, sea-spray, and sleet (explicit
       values above the previous maximum, append-only wire-safe) so a
       station reporting those NTCIP essVisibilitySituation conditions
       no longer folds them lossily into a neighbor; correct the
       pavement-condition citation to essSurfaceStatus (the 1204 object;
       essPavementStatus does not exist); repoint the faults description
       at the shared openits-common-fault-events notifications.";
    reference "NTCIP 1204 v04 (essVisibilitySituation / essSurfaceStatus).";
  }
  revision 2026-07-21 {
    description
      "Sensing/ESS review fixes: add 2-minute averaged wind direction
       (wind-direction-avg-deg); add pavement sensing-method (embedded vs
       non-invasive-remote); exclude 360 from bearing-degrees (canonicalize
       north as 0, pre-1.0 tightening); make observation-metadata/sensor-id
       a require-instance-false leafref into diagnostics/sensor. Stamp
       explicit enum values on observation-metadata/quality for append-only
       discipline. Additive except the bearing tightening.";
    reference "NTCIP 1204.";
  }
  revision 2026-07-16 {
    description
      "Snow + minors (Cut 1c): add precipitation snow-depth-mm /
       snow-rate-mm-h and fixed-window accumulated-1h-mm / accumulated-24h-mm
       (comparable across stations, unlike accumulated-mm's station-defined
       reset); extend sensor-health with 'disabled' and pavement-condition
       with 'dew' / 'error'; widen the celsius range to -100..100 (the ±80
       cap was below the NTCIP 1204 span); document the calm-wind convention
       and the salinity ppm-vs-parts-per-100k 10x gateway trap.
       Measurement context (Cut 1b): add station/configuration sensor
       mounting heights (wind / air-temperature / visibility) so
       height-dependent observations are comparable; add
       atmospheric/wind-speed-avg-ms (2-min sustained) and define the
       wind-gust window (10-min) so restrictions can trigger on average AND
       gust; add a per-observation quality flag (valid / suspect / estimated
       / not-installed / missing) to observation-metadata so an absent value
       is no longer ambiguous.
       Winter road-state (Cut 1a): extend precipitation-type with the
       freezing classes (freezing-rain / freezing-drizzle / ice-crystals)
       plus mixed — freezing rain is the most dangerous road-ops class and
       was previously unreportable (appended, wire-safe); add pavement
       grip-coefficient (friction), chemical-percent / chemical-factor and
       ice-depth-mm so the model supports anti-icing decisions, not just a
       weather display (NTCIP 1204 essSurfaceChemical* / essSurfaceIceOrWaterDepth
       / friction).";
    reference "NTCIP 1204 v03 (ESS).";
  }
  revision 2026-07-13 {
    description
      "Adopt the shared openits-types:fault-entry grouping in the
       config-false faults list, replacing the inline fault-id +
       severity + description + first-observed leaves. The
       service-specific category identityref is unchanged.

       Also adopt the shared openits-types:device-hardware grouping
       (make/model/firmware/serial) in the identity container,
       replacing the inline config-false leaves.

       Delete the local percent typedef; use openits-types:percentage-
       precise.";
  }
  revision 2026-07-12 {
    description
      "Move the fault taxonomy to gen-2: delete the gen-1
       fault-category identity and its fault-sensor-failure /
       fault-power / fault-communication / fault-calibration-drift /
       fault-environmental children, replaced by the service-prefixed
       ess-fault-event-kind tree already present in the
       openits-ess-types module. The faults/fault 'category' leaf now
       bases on openits-ess-types:ess-fault-event-kind. Breaking:
       identity names change (e.g. fault-sensor-failure ->
       ess-fault-sensor-failure); wire-neutral since the wire
       representation of an identityref is a string (pre-v1,
       acceptable). Completes the fault-taxonomy consolidation for
       this service.";
    reference "RFC 7950 section 11 (breaking YANG evolution: identity rename).";
  }
  revision 2026-07-10 {
    description
      "Replace the inline severity enumeration on the fault-inventory
       list with the shared openits-types:fault-severity typedef.
       Member set and order unchanged — wire-stable.

       Also, replace the inline station-identity latitude/longitude
       leaves (decimal64 fraction-digits 6) with
       openits-types:geo-point (fraction-digits 7), correcting a
       precision drift versus the shared geo-location grouping used
       elsewhere. Member set unchanged (latitude, longitude); the
       fraction-digits mantissa widens from 6 to 7. The unrelated
       'elevation-m' leaf (int32, distinct from geo-location's
       decimal64 'elevation') is untouched.

       Also, add base openits-types:fault-event-kind to the
       fault-category root so this service's faults are reachable by
       fleet-wide derived-from-or-self(fault-event-kind) queries.
       Additive (identity gains a base); no child renamed.";
    reference "RFC 7950 section 11 (additive YANG evolution).";
  }
  revision 2026-04-19 {
    description
      "Initial revision.  Minimum viable model covering identity,
       atmospheric conditions, precipitation, visibility, pavement
       sensors, solar radiation, diagnostics, and a live fault
       inventory.";
    reference
      "ARC-IT 9.1 Service Package MC01 (Environmental Monitoring
       Station); NTCIP 1204 v04 (functional reference only; no wire
       compatibility).";
  }

  /* --------------------------------------------------------------
   * Typedefs
   * -------------------------------------------------------------- */


  typedef bearing-degrees {
    type decimal64 {
      fraction-digits 1;
      range "0.0 .. 359.9";
    }
    units "degrees";
    description
      "Compass bearing, 0..359.9. 0 = true north (canonical); increasing
       clockwise. 360 is excluded — north is reported as 0, matching
       openits-types:heading-degrees.";
  }

  typedef celsius {
    type decimal64 {
      fraction-digits 1;
      range "-100.0 .. 100.0";
    }
    units "celsius";
    description
      "Temperature in degrees Celsius.  Range accommodates global
       deployments (coldest recorded road-surface temperature is
       around -70 °C; hottest pavement ~75 °C).";
  }

  typedef precipitation-type {
    type enumeration {
      enum unknown { value 0; }
      enum none    { value 1; }
      enum rain    { value 2; }
      enum snow    { value 3; }
      enum sleet   { value 4; }
      enum hail    { value 5; }
      enum drizzle { value 6; }
      enum other   { value 7; }
      enum freezing-rain    { value 8;  description "Rain freezing on contact — glazes the road near 0 °C; the most dangerous class for road ops. NOT interchangeable with sleet/ice-pellets."; }
      enum freezing-drizzle { value 9;  description "Drizzle freezing on contact."; }
      enum ice-crystals     { value 10; description "Ice crystals / diamond dust in very cold, clear air."; }
      enum mixed            { value 11; description "Mixed precipitation (e.g. rain and snow together)."; }
    }
    description
      "Type of precipitation currently observed (NTCIP 1204 essPrecipSituation).
       The freezing classes are distinguished because freezing rain glazes the
       road near 0 °C where ice pellets bounce off — a station observing
       freezing rain must NOT report it as plain rain or sleet.";
  }

  typedef precipitation-intensity {
    type enumeration {
      enum unknown    { value 0; }
      enum none       { value 1; }
      enum light      { value 2; }
      enum moderate   { value 3; }
      enum heavy      { value 4; }
      enum violent    { value 5; }
    }
    description "Qualitative intensity of precipitation.";
  }

  typedef visibility-situation {
    type enumeration {
      enum unknown          { value 0; }
      enum clear            { value 1; }
      enum fog              { value 2; }
      enum heavy-fog        { value 3; }
      enum smoke            { value 4; }
      enum blowing-snow     { value 5; }
      enum blowing-dust     { value 6; }
      enum heavy-rain       { value 7; }
      enum heavy-snow       { value 8; }
      enum mist-haze        { value 9;  description "Mist or haze reducing visibility (NTCIP essVisibilitySituation mist/haze)."; }
      enum sand-storm       { value 10; description "Sand storm — distinct from locally blowing dust."; }
      enum sea-spray        { value 11; description "Salt / sea spray reducing visibility on coastal segments."; }
      enum sleet            { value 12; description "Sleet / freezing-mix precipitation reducing visibility."; }
    }
    description
      "Qualitative description of the visibility situation, mirroring
       NTCIP 1204 essVisibilitySituation.  Used in conjunction with
       `visibility/range-m` (the quantitative value).";
  }

  typedef pavement-condition {
    type enumeration {
      enum unknown           { value 0; }
      enum dry               { value 1; }
      enum trace-moisture    { value 2; }
      enum wet               { value 3; }
      enum chemically-wet    { value 4; }
      enum ice-warning       { value 5; }
      enum ice-watch         { value 6; }
      enum snow-warning      { value 7; }
      enum snow-watch        { value 8; }
      enum absorption        { value 9; }
      enum frost             { value 10; }
      enum dew               { value 11; }
      enum error             { value 12; }
    }
    description
      "Qualitative pavement condition as reported by the pavement
       sensor's embedded classifier.  Values mirror NTCIP 1204
       essSurfaceStatus (the surface-sensor status object; an earlier
       revision miscited it as 'essPavementStatus', which does not
       exist in 1204).";
  }

  typedef sensor-health {
    type enumeration {
      enum ok           { value 0; }
      enum stale        { value 1; }
      enum uncalibrated { value 2; }
      enum degraded     { value 3; }
      enum failed       { value 4; }
      enum disabled     { value 5; }
    }
    description
      "Per-sensor health rollup.  `stale` means the sensor is
       producing values outside its expected refresh interval;
       `degraded` means the sensor is reporting but quality flags
       suggest reduced confidence.";
  }

  /* --------------------------------------------------------------
   * Reusable groupings
   * -------------------------------------------------------------- */

  grouping observation-metadata {
    description
      "Metadata carried on every observation container.  `observed-at`
       is the sensor-clock time of the most recent sample; consumers
       use it with `diagnostics/sensor-health` to gate stale data.";

    leaf observed-at {
      type yang:date-and-time;
      description "Wall-clock time of the most recent sample.";
    }
    leaf sensor-id {
      type leafref {
        path "../../diagnostics/sensor/sensor-id";
        require-instance false;
      }
      description
        "Identifier of the physical sensor producing this observation —
         a foreign key into diagnostics/sensor. require-instance false: a
         station may report an observation whose sensor is not enumerated in
         the diagnostics inventory, so the reference is advisory, not a hard
         existence constraint.";
    }
    leaf quality {
      type enumeration {
        enum valid         { value 0; description "Observation passed the sensor's quality checks."; }
        enum suspect {
          value 1;
          description "Reported but flagged low-confidence by the sensor; use with caution.";
        }
        enum estimated     { value 2; description "Value is interpolated / estimated, not directly measured."; }
        enum not-installed { value 3; description "No sensor for this observation is installed at the station."; }
        enum missing       { value 4; description "Sensor is installed but produced no reading this cycle."; }
      }
      description
        "Per-observation quality / validity. Without it, an absent value is
         ambiguous — 'no sensor installed' vs 'installed but silent' vs 'a
         degraded reading' — so a consumer cannot tell trustworthy data from
         a sensor problem. This makes it explicit.";
    }
  }

  grouping diagnostics-sensor-config {
    description "Per-sensor intended configuration.";
    leaf sensor-id { type string; description "Identifier of the sensor within this station."; }
    leaf sample-interval-s { type uint32; units "seconds";
      description "Configured sample interval for this sensor in seconds."; }
  }

  grouping pavement-sensor-config {
    description "Per-pavement-sensor intended configuration.";
    leaf sensor-id { type string; description "Identifier of the pavement sensor within this station."; }
    leaf lane-reference { type string; description "Free-form lane description (e.g., \"northbound-inside\")."; }
    leaf sensing-method {
      type enumeration {
        enum embedded            { value 0; description "Invasive in-pavement puck / probe."; }
        enum non-invasive-remote {
          value 1;
          description "Non-invasive remote sensor (spectroscopic / IR from a mast).";
        }
        enum unknown             { value 2; description "Sensing method not declared."; }
      }
      description "Whether the pavement sensor is an embedded puck or a non-invasive remote sensor.";
    }
  }

  /* --------------------------------------------------------------
   * Main tree
   * -------------------------------------------------------------- */

  container station {
    description
      "Top-level container for a single environmental sensor
       station.";

    /* ----- station identity (config / applied-state) ----- */
    container config {
      description "Intended station configuration.";
      uses openits-types:device-identity-config;
    }
    container state {
      config false;
      description "Applied station configuration (mirror) plus device-reported hardware inventory.";
      uses openits-types:device-identity-config;
      uses openits-types:device-hardware;
    }

    /* ----- sensor install parameters ----- */
    container configuration {
      description
        "Physical sensor install parameters needed to interpret the bulk
         observations. Wind and temperature vary strongly with height, so an
         observation is only comparable across stations once its sensor
         height is known.";
      leaf wind-sensor-height-m {
        type decimal64 { fraction-digits 1; range "0.0 .. 30.0"; }
        units "meters";
        description
          "Height above ground of the anemometer. Wind speed at 3 m vs 10 m
           differs 20-30 %, directly changing whether a high-wind restriction
           threshold is crossed (NTCIP 1204 essWindSensorHeight; WMO standard
           10 m).";
      }
      leaf air-temperature-sensor-height-m {
        type decimal64 { fraction-digits 1; range "0.0 .. 30.0"; }
        units "meters";
        description "Height above ground of the air-temperature sensor.";
      }
      leaf visibility-sensor-height-m {
        type decimal64 { fraction-digits 1; range "0.0 .. 30.0"; }
        units "meters";
        description "Height above ground of the visibility sensor.";
      }
    }

    /* ----- atmospheric conditions ----- */
    container atmospheric {
      config false;
      openits-types:arc-it-flow
        "Environmental Sensors -> TMC : road weather information";
      description
        "Bulk air observations.  Every leaf is optional — not every
         station carries every sensor.";

      uses observation-metadata;

      leaf air-temperature-c { type celsius; description "Ambient air temperature in degrees Celsius."; }
      leaf dewpoint-c        { type celsius; description "Dewpoint temperature in degrees Celsius."; }
      leaf humidity-percent  { type openits-types:percentage-precise; description "Relative humidity, 0-100%."; }

      leaf pressure-hpa {
        type decimal64 {
          fraction-digits 1;
          range "300.0 .. 1100.0";
        }
        units "hectopascals";
        description
          "Station-pressure reading.  300..1100 hPa covers every
           inhabited elevation on Earth with margin.";
      }

      leaf wind-speed-ms {
        type decimal64 {
          fraction-digits 1;
          range "0.0 .. 120.0";
        }
        units "meters-per-second";
        description
          "Instantaneous wind speed.  120 m/s upper bound is well
           above any observed surface wind (record is ~113 m/s).";
      }
      leaf wind-speed-avg-ms {
        type decimal64 {
          fraction-digits 1;
          range "0.0 .. 120.0";
        }
        units "meters-per-second";
        description
          "Sustained wind speed, the 2-minute rolling average (NTCIP 1204 /
           WMO). High-wind restrictions trigger on the sustained average AND
           the gust, so the instantaneous value alone is not sufficient.";
      }
      leaf wind-gust-ms {
        type decimal64 {
          fraction-digits 1;
          range "0.0 .. 150.0";
        }
        units "meters-per-second";
        description
          "Peak wind-gust speed over the 10-minute gust window (NTCIP 1204 /
           WMO), pairing with wind-speed-avg-ms. The window is defined so gust
           thresholds are comparable across stations.";
      }
      leaf wind-direction-deg {
        type bearing-degrees;
        description
          "Wind direction in degrees from north (0=N, 90=E, 180=S, 270=W);
           0 and 360 both denote north. Under calm conditions (wind-speed-ms
           near 0) direction is undefined and this leaf should be omitted
           rather than reported as 0.";
      }
      leaf wind-direction-avg-deg {
        type bearing-degrees;
        description
          "2-minute average wind direction (NTCIP 1204 essAvgWindDirection),
           pairing with wind-speed-avg-ms. Crosswind restrictions trigger on
           the sustained average, not the instantaneous direction. Omitted
           under calm conditions.";
      }
    }

    /* ----- precipitation ----- */
    container precipitation {
      config false;
      openits-types:arc-it-flow
        "Environmental Sensors -> TMC : road weather information";
      description
        "Precipitation observations: type, intensity, rate, and
         accumulation since the station's last reset.";

      uses observation-metadata;

      leaf type      { type precipitation-type; description "Precipitation class (rain, snow, sleet, hail, mixed, etc.)."; }
      leaf intensity { type precipitation-intensity; description "Operator-visible intensity bucket (none / light / moderate / heavy)."; }
      leaf rate-mm-h {
        type decimal64 { fraction-digits 2; range "0.0 .. 500.0"; }
        units "millimeters-per-hour";
        description "Current precipitation rate in millimeters per hour.";
      }
      leaf accumulated-mm {
        type decimal64 { fraction-digits 1; range "0.0 .. 10000.0"; }
        units "millimeters";
        description
          "Accumulation since the last reset (station-specific; may
           be hourly, daily, or storm-bucketed). NOT comparable across
           stations — use the fixed-window accumulations below for that.";
      }
      leaf accumulated-1h-mm {
        type decimal64 { fraction-digits 1; range "0.0 .. 1000.0"; }
        units "millimeters";
        description "Precipitation accumulated over the last 1 hour (fixed window, comparable across stations).";
      }
      leaf accumulated-24h-mm {
        type decimal64 { fraction-digits 1; range "0.0 .. 10000.0"; }
        units "millimeters";
        description "Precipitation accumulated over the last 24 hours (fixed window).";
      }
      leaf snow-depth-mm {
        type decimal64 { fraction-digits 1; range "0.0 .. 10000.0"; }
        units "millimeters";
        description "Depth of snow on the ground (NTCIP 1204 essSnowDepth) — the operational quantity for plow dispatch, distinct from liquid-equivalent accumulation.";
      }
      leaf snow-rate-mm-h {
        type decimal64 { fraction-digits 2; range "0.0 .. 500.0"; }
        units "millimeters-per-hour";
        description "Rate of snow accumulation (liquid-equivalent), for anticipating when a depth threshold will be crossed.";
      }
    }

    /* ----- visibility ----- */
    container visibility {
      config false;
      openits-types:arc-it-flow
        "Environmental Sensors -> TMC : road weather information";
      description
        "Horizontal visibility observations plus a coarse situation
         class for operators.";

      uses observation-metadata;

      leaf range-m {
        type uint32 { range "0..100000"; }
        units "meters";
        description
          "Horizontal visibility range.  100 km cap is conservative
           (practical sensors saturate well below this).";
      }
      leaf situation { type visibility-situation; description "Operator-visible visibility class (clear / fog / heavy-fog / blowing-snow / etc.)."; }
    }

    /* ----- pavement sensors ----- */
    container pavement {
      openits-types:arc-it-flow
        "Environmental Sensors -> TMC : road weather information";
      description
        "Per-sensor pavement configuration and observations. Multi-sensor
         stations report one list entry per installed puck / probe.";

      list sensor {
        key "sensor-id";
        description "One entry per installed pavement puck or probe.";

        leaf sensor-id { type leafref { path "../config/sensor-id"; }
          description "Identifier of the pavement sensor within this station."; }

        container config {
          description "Intended per-sensor configuration.";
          uses pavement-sensor-config;
        }
        container state {
          config false;
          description "Applied config (mirror) plus device-reported pavement observations.";
          uses pavement-sensor-config;
          leaf observed-at { type yang:date-and-time; description "Wall-clock time of the observation."; }
          leaf surface-temperature-c { type celsius; description "Pavement surface temperature in degrees Celsius."; }
          leaf condition { type pavement-condition; description "Operator-visible pavement condition (dry / wet / snow / ice / etc.)."; }
          leaf freeze-point-c { type celsius; description "Freeze point of the surface (depressed below 0 °C by salt / brine)."; }
          leaf water-depth-mm {
            type decimal64 { fraction-digits 2; range "0.0 .. 100.0"; }
            units "millimeters";
            description "Water-film depth on the pavement surface.";
          }
          leaf salinity-ppm {
            type uint32 { range "0..500000"; }
            units "parts-per-million";
            description
              "Salinity of the surface water in parts-per-million
               (mg/L), used to derive freeze-point-c. NOTE the units:
               ppm, NOT the NTCIP 1204 essSurfaceSalinity parts-per-100000 —
               a gateway must multiply the 1204 value by 10, or the derived
               freeze point is off by an order of magnitude.";
          }
          leaf grip-coefficient {
            type decimal64 { fraction-digits 2; range "0.00 .. 1.00"; }
            description
              "Measured surface friction / grip coefficient (0 = ice-slick,
               ~0.82 = dry). Directly times anti-icing runs — grip crossing a
               threshold is the operational trigger, not surface temperature
               alone (NTCIP 1204 essMobileFriction / DSC111-class sensors).";
          }
          leaf chemical-percent {
            type openits-types:percentage-precise;
            description
              "De-icing chemical concentration on the surface, as a percentage
               (NTCIP 1204 essSurfaceChemicalPercent). Drives the freeze-point
               depression and whether a re-application is due.";
          }
          leaf chemical-factor {
            type decimal64 { fraction-digits 2; range "0.00 .. 100.00"; }
            description
              "Chemical-amount factor the sensor reports alongside
               chemical-percent (NTCIP 1204 essSurfaceChemicalFactor).";
          }
          leaf ice-depth-mm {
            type decimal64 { fraction-digits 2; range "0.0 .. 100.0"; }
            units "millimeters";
            description
              "Depth of ice on the surface (distinct from water-depth-mm; NTCIP
               1204 essSurfaceIceOrWaterDepth resolves the frozen fraction).";
          }
          leaf subsurface-temperature-c { type celsius; description "Subsurface temperature at the depth named by subsurface-depth-mm."; }
          leaf subsurface-depth-mm {
            type uint16 { range "0..1000"; }
            units "millimeters";
            description
              "Depth at which `subsurface-temperature-c` is sampled.";
          }
        }
      }
    }

    /* ----- solar radiation ----- */
    container radiation {
      config false;
      openits-types:arc-it-flow
        "Environmental Sensors -> TMC : road weather information";
      description
        "Solar radiation observations (instantaneous + hourly average).";

      uses observation-metadata;

      leaf solar-radiation-wm2 {
        type decimal64 { fraction-digits 1; range "0.0 .. 2000.0"; }
        units "watts-per-square-meter";
        description
          "Instantaneous solar radiation.  Typical daytime clear-sky
           peak is ~1000 W/m²; 2000 ceiling leaves headroom for
           high-altitude / albedo-enhanced readings.";
      }
      leaf solar-radiation-hourly-avg-wm2 {
        type decimal64 { fraction-digits 1; range "0.0 .. 2000.0"; }
        units "watts-per-square-meter";
        description "Hourly-averaged solar radiation in W/m².";
      }
    }

    /* ----- diagnostics ----- */
    container diagnostics {
      openits-types:arc-it-flow
        "Environmental Sensors -> Maintenance : equipment maintenance status";
      description
        "Per-sensor configuration and health. sample-interval-s is intended
         config; health/calibration are device-reported state.";

      list sensor {
        key "sensor-id";
        description "One entry per installed sensor.";

        leaf sensor-id { type leafref { path "../config/sensor-id"; }
          description "Identifier of the sensor within this station."; }

        container config {
          description "Intended per-sensor configuration.";
          uses diagnostics-sensor-config;
        }
        container state {
          config false;
          description "Applied config (mirror) plus device-reported sensor health.";
          uses diagnostics-sensor-config;
          leaf type { type string;
            description "Sensor type (e.g., \"air-temperature\", \"pavement\", \"visibility\")."; }
          leaf health { type sensor-health;
            description "Sensor health state (ok / degraded / failed / disabled)."; }
          leaf last-observation { type yang:date-and-time;
            description "Wall-clock time of the most recent observation from this sensor."; }
          leaf last-calibration { type yang:date-and-time;
            description "Wall-clock time of the most recent calibration of this sensor."; }
          leaf next-calibration { type yang:date-and-time;
            description "Wall-clock time the next calibration is due."; }
        }
      }
    }

    /* ----- fault inventory ----- */
    container faults {
      config false;
      openits-types:arc-it-flow
        "Environmental Sensors -> Maintenance : equipment maintenance status";
      description
        "Live fault inventory.  Each entry mirrors an
         openits-common-fault-events:fault-raised notification
         (discriminated by this service's fault-event-kind identities) and clears when the
         condition resolves.";

      list fault {
        key "fault-id";
        description "One entry per active fault on the station.";
        uses openits-types:fault-entry;
        leaf category {
          type identityref { base openits-ess-types:ess-fault-event-kind; }
          description "Fault class (sensor / communication / power / environment / etc.).";
        }
      }
    }
  }
}
