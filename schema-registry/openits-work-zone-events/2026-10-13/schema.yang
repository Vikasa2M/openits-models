module openits-work-zone-events {
  yang-version 1.1;
  namespace "urn:openits:yang:work-zone-events";
  prefix openits-work-zone-events;

  import openits-types {
    prefix openits-types;
  }
  import openits-work-zone-types {
    prefix openits-work-zone-types;
  }
  import ietf-yang-types {
    prefix yang;
  }

  organization
    "OpenITS Working Group (proposal)";
  contact
    "OpenITS Working Group (proposal)";

  description
    "Event payloads for work zones: lane closures, roadworks, and other
     planned disruptions to the traveled way.

     Imports only shared -types modules, per the events-layering rule --
     an events module never depends on a capability's or service's
     config/state schema.

     THIS FAMILY IS EVENTS-ONLY BY DESIGN. There is no
     'openits-work-zone.yang' core module, no conformance kind, and no
     mock driver, and none of those are oversights. A work zone is not a
     device: there is nothing to configure, nothing to poll, and no
     vendor implementation to conform. It is an external fact about the
     roadway, reported by whatever upstream system tracks it. The
     precedent is the common-* event modules, which are likewise
     events-only. Do not 'complete' this family by adding a device
     profile.

     Copyright (c) 2026. Distributed under Apache 2.0.";

  openits-types:openits-version "0.4.0";

  revision 2026-10-13 {
    description
      "Inherit the mandatory sequence-epoch leaf from the openits-types
       event-header grouping, which changes every notification payload
       in this module. Breaking: producers must emit sequence-epoch.";
    reference "RFC 7950 §11.";
  }
  revision 2026-09-08 {
    description
      "Retype zone-state-changed/direction onto
       openits-types:travel-direction (breaking, pre-1.0), a namespace
       move of the identical vocabulary; see openits-work-zone-types'
       revision of the same date.

       Typed to the wide axis rather than to carriageway-direction,
       because a work zone legitimately affects both carriageways --
       unlike a reversible lane, whose leaves narrow to one.";
    reference "WZDx v4 (RoadEventCoreDetails.direction); RFC 7950 §11.";
  }
  revision 2026-09-07 {
    description
      "Describe the direction leaf against the cardinal roadway-direction
       vocabulary openits-work-zone-types adopts in the same change set,
       and state that wz-direction-unknown must not be read as
       wz-direction-both. Description-only in this module; the vocabulary
       change itself is breaking and is recorded there.

       Adds the WZDx v4 fields whose absence made this a closure notice
       rather than a work-zone record, all additive:

       worker-presence (a presence container: workers-present, how the
       feed determined it, and when it was last confirmed) and
       reduced-speed-limit-kmh. These are the two fields that drive
       speed enforcement, connected-vehicle behavior and TIM messaging,
       and neither was representable. worker-presence is a presence
       container precisely so a feed that does not report on workers
       omits it rather than asserting they are absent.

       work-zone-type, so a consumer knows whether the geometry it just
       received is a fixed closure or a snapshot of a moving operation.

       start-verified / end-verified, distinguishing a confirmed window
       from a planned one -- planned windows slip routinely, and a
       traveler-information consumer needs to know which it holds.

       temporary-signal loses its `default false`. Most upstream feeds
       carry no such field, so the default made every one of them assert
       that no temporary signal is present. Absent now means not
       reported. This is a wire-visible change to a leaf that previously
       always materialized.";
    reference "WZDx v4 (RoadEventCoreDetails.direction).";
  }
  revision 2026-09-02 {
    description
      "Initial revision. One notification, zone-state-changed, carrying
       activation, update, and clearing through the 'kind' identity.";
  }

  notification zone-state-changed {
    openits-types:arc-it-flow
      "Maintenance and Construction Management -> TMC : work zone information";
    description
      "A work zone became active, changed, or ended.

       One notification rather than three because the three differ only
       in 'kind': every leaf below means the same thing in each case,
       and a cleared zone still carries its geometry and window so a
       consumer can close its record without a prior lookup.

       This family has no device, so 'uses event-header' binds to the
       feed instead: source-device-id is the stable identifier of the
       feed or collector reporting the zone, since there is no field
       device to name. occurred-at is when the change took effect
       upstream, or was published by the feed -- not when the
       translator observed it. sequence is the translator's own
       per-feed monotonic counter. observed-by, when present, is the
       collector, when it differs from the feed.";

    leaf kind {
      type identityref {
        base openits-work-zone-types:work-zone-event-kind;
      }
      mandatory true;
      description
        "Event classifier: openits-work-zone-types:wz-activated,
         wz-updated, or wz-cleared.";
    }
    uses openits-types:event-header;

    leaf zone-id {
      type openits-work-zone-types:work-zone-id;
      mandatory true;
      description
        "The upstream feed's identifier for this zone. Opaque here and
         never parsed -- its structure is the reporting system's
         business.";
    }

    // A work zone must carry at least one geometry point (a single
    // point is a valid degenerate extent; zero points is not a
    // location), expressed here as `min-elements 1` rather than a
    // notification-level `must "count(point) >= 1"`. Two reasons:
    // tools/yang-proto-gen (goyang) rejects `must` as a direct child of
    // `notification` -- "unknown notification field: must" -- even
    // though YANG 1.1 permits it (RFC 7950 §7.16.3); confirmed against
    // this repo's pinned generator. And min-elements is the more
    // faithful native constraint for "at least N instances of a list"
    // in the first place -- a must reimplementing cardinality via
    // count() is the workaround, not the idiom. yanglint's pinned build
    // does not enforce min-elements on a notification instance under
    // `-t notif` any more than it enforces must/mandatory there (see
    // scripts/check-notif-mandatory.py, extended to check this too).
    uses openits-types:geo-path {
      refine "point" {
        min-elements 1;
        description
          "A work zone must carry at least one geometry point. A single
           point is a valid degenerate extent; zero points is not a
           location.

           This floor is a YANG-layer constraint only -- it is not
           projected into the generated JSON Schema, where 'point'
           renders as a bare array with no minItems. A consumer
           validating a payload against ce-dataschema must enforce the
           minimum itself.";
      }
    }

    leaf window-start {
      type yang:date-and-time;
      mandatory true;
      description "When the closure takes, or took, effect.";
    }
    leaf window-end {
      type yang:date-and-time;
      description
        "When the closure ends. Absent means open-ended, which feeds
         publish for long-running projects.

         MAY be in the past. An already-expired zone is valid, not
         erroneous: a translator that receives one has no honest
         alternative to forwarding it, and a consumer needs the record
         to close its own.

         When present, MUST be at or after window-start. This is a
         semantic contract the schema itself cannot express as a
         `must`: XPath 1.0's relational operators numeric-coerce both
         operands whenever neither is already numeric, and a
         date-and-time string is not numeric, so any '. >= ../sibling'
         comparison between two date-and-time leaves evaluates to NaN
         and is always false -- exactly the reason the 2026-07-21
         revision of openits-v2x-messaging.yang removed the identical
         construct from the TIM broadcast window. A consumer must
         enforce this ordering itself.";
    }

    leaf direction {
      type identityref {
        base openits-types:travel-direction;
      }
      description
        "Cardinal direction of travel affected, or one of the loop
         carriageways where cardinal direction changes along the route.
         direction-both is a real published value, not a modeling
         convenience; direction-unknown says the feed did not report one,
         which a consumer must not read as 'both'.

         Typed to the full travel-direction axis rather than to
         carriageway-direction, because a work zone legitimately affects
         both carriageways -- unlike a reversible lane, whose leaves
         narrow to a single carriageway.";
    }
    leaf lane-impact {
      type identityref {
        base openits-work-zone-types:lane-impact;
      }
      description "What the closure does to the traveled way.";
    }
    leaf temporary-signal {
      type boolean;
      description
        "A temporary signal is operating within the zone.

         Carried as its own leaf rather than left to 'notice' because a
         temporary signal changes how a signal-performance measure over
         the affected approach must be read. A consumer cannot find that
         reliably in free text.

         No default: absent means the feed did not report whether a
         temporary signal is present, which is not the same claim as
         'false'. Most upstream feeds carry no such field at all, and a
         default would have made every one of them assert there is no
         signal.";
    }
    leaf work-zone-type {
      type identityref {
        base openits-work-zone-types:work-zone-type;
      }
      description
        "Whether the zone is static or a moving operation. A consumer
         must not cache a moving zone's geometry: it was true when
         published and is not now.";
      reference "WZDx v4 (WorkZoneRoadEvent.work_zone_type).";
    }

    container worker-presence {
      presence "The feed reports on worker presence.";
      description
        "Whether workers are in the zone right now, and how the feed
         knows. A presence container, so a feed that does not report on
         workers omits it entirely rather than asserting they are
         absent -- the difference matters, because worker presence is
         what justifies a reduced speed limit and its enforcement.";
      reference "WZDx v4 (WorkerPresence).";

      leaf workers-present {
        type boolean;
        mandatory true;
        description "True when workers are in the work zone.";
      }
      leaf method {
        type identityref {
          base openits-work-zone-types:worker-presence-method;
        }
        description
          "How the determination was made. An automated detection and a
           schedule-derived assumption warrant different confidence
           before acting on the claim.";
      }
      leaf last-confirmed-at {
        type yang:date-and-time;
        description
          "When worker presence was last confirmed by the stated method.
           A stale confirmation on a long-running zone is the signal a
           consumer needs to stop trusting the flag.";
      }
    }

    leaf reduced-speed-limit-kmh {
      type openits-types:speed-kmh;
      description
        "Posted speed limit in effect through the zone, when the zone
         reduces it. Absent when the zone posts no reduction, or when
         the feed does not report one -- a consumer must not infer the
         normal limit from absence.";
      reference "WZDx v4 (WorkZoneRoadEvent.reduced_speed_limit_kph).";
    }

    leaf start-verified {
      type boolean;
      description
        "True when the zone's start time is confirmed rather than
         planned. A planned window slips routinely, and a consumer
         posting traveler information needs to know which it has.";
      reference "WZDx v4 (is_start_date_verified).";
    }
    leaf end-verified {
      type boolean;
      description
        "True when the zone's end time is confirmed rather than planned.";
      reference "WZDx v4 (is_end_date_verified).";
    }

    leaf notice {
      type string;
      description
        "Free-text description as published upstream. Human-facing only
         -- nothing derives behavior from it.";
    }
  }
}
