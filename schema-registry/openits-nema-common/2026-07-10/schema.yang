module openits-nema-common {
  yang-version 1.1;
  namespace "urn:openits:yang:nema-common";
  prefix openits-nema;

  organization
    "OpenITS Working Group (proposal)";

  contact
    "OpenITS Working Group (proposal)";

  description
    "Shared NEMA-adjacent typedefs and groupings used by multiple
     openits device modules (signal control, ramp metering,
     potentially traffic-responsive corridor control later).

     Scope is deliberately narrow: phase-number, phase-timing with
     its MUTCD-derived and engineering-floor `must`-constraints, and
     nothing else.
     Service-specific constructs (rings, barriers, coordination
     plans, ramp-queue thresholds) remain in their home modules.

     Copyright (c) 2026.  Distributed under Apache 2.0.";

  revision 2026-07-10 {
    description
      "Correct the MUTCD phase-timing constraints to match MUTCD 11th ed.
       (2023): yellow-change is 3.0-6.0 s (4F.17); red-clear has no MUTCD
       minimum, 6.0 s ceiling only (4F.17); min-green is an engineering
       floor (>=1 s), not a MUTCD mandate. Fix the max-green and ped-clear
       'must' expressions to not misfire when the referenced sibling leaf is
       absent. Correct the fabricated 4D.26 citations. Split phase-timing
       into vehicle-phase-timing (min-green, max-green, yellow-change,
       red-clear, passage) and phase-timing (uses vehicle-phase-timing,
       adds walk/ped-clear), so ramp meters can consume vehicle timing
       only and no longer inherit pedestrian-interval leaves that do not
       apply to a freeway on-ramp.";
    reference "MUTCD 11th ed. (2023) section 4F.17.";
  }

  revision 2026-04-19 {
    description
      "Initial release.  Extracted from openits-signal-control
       2026-04-18 during milestone M9 so signal-control and
       ramp-metering can share one source of truth for MUTCD
       phase-timing minimums.  The values and error messages are
       byte-for-byte equivalent to what signal-control shipped;
       only the location moved.";
    reference
      "MUTCD 11th ed. 4F.17 (yellow/red clearance), 4E.06 (pedestrian
       intervals).";
  }

  /* --------------------------------------------------------------
   * Typedefs
   * -------------------------------------------------------------- */

  typedef phase-number {
    type uint8 {
      range "1..40";
    }
    description
      "Vehicle or pedestrian phase identifier.  Range accommodates
       NTCIP 1202 v03 (40 phases).  Most deployments use 1..8 or
       1..16 in standard dual-ring configurations.  Ramp meters
       typically use 1..2.";
    reference "NTCIP 1202 v03 (phase numbering); NEMA TS-2 §6.3.2.";
  }

  /* --------------------------------------------------------------
   * Groupings
   * -------------------------------------------------------------- */

  grouping vehicle-phase-timing {
    description
      "Vehicle change/clearance timing shared by signalized intersections
       and traffic-metered ramps. Pedestrian intervals live in the
       phase-timing grouping, which adds them on top of this one.";

    leaf min-green {
      type uint16;
      units "seconds";
      must ". >= 1" {
        error-message
          "Minimum green must be positive (operational floor to forbid a "
        + "zero-length serve). MUTCD sets no universal minimum-green value; "
        + "it is engineering-determined. TODO(WG): confirm the jurisdiction "
        + "floor.";
      }
      description
        "Minimum green time.  Enforced floor of 1 s forbids a
         zero-length serve; MUTCD sets no universal minimum-green
         value, so any larger jurisdiction-specific floor is
         engineering-determined.";
    }
    leaf max-green {
      type uint16;
      units "seconds";
      must ". > 0 and (not(../min-green) or . >= ../min-green)" {
        error-message
          "Maximum green must be non-zero and, when min-green is present, "
        + ">= min-green, so the phase has a usable service interval.";
      }
      description
        "Maximum green time.  Must be non-zero and, when min-green is
         present, >= min-green so the phase has a usable service
         interval.";
    }
    leaf yellow-change {
      type decimal64 { fraction-digits 1; }
      units "seconds";
      must ". >= 3.0 and . <= 6.0" {
        error-message
          "Yellow change must be 3.0-6.0 seconds per MUTCD 11th ed. "
        + "section 4F.17 paragraph 13.";
      }
      description
        "Yellow change interval.  MUTCD 11th ed. 4F.17 guidance is
         3.0-6.0 seconds.";
    }
    leaf red-clear {
      type decimal64 { fraction-digits 1; }
      units "seconds";
      must ". <= 6.0" {
        error-message
          "Red clearance shall be determined using engineering practices "
        + "(MUTCD 11th ed. section 4F.17 paragraph 6) and should not exceed "
        + "6.0 seconds. MUTCD sets no minimum. TODO(WG): set a jurisdiction "
        + "sanity floor if desired.";
      }
      description
        "All-red clearance interval.  Determined using engineering
         practices per MUTCD 11th ed. 4F.17 paragraph 6; MUTCD sets
         no minimum.  Ceiling of 6.0 s protects against runaway
         values.";
    }
    leaf passage {
      type decimal64 { fraction-digits 1; }
      units "seconds";
      description "Vehicle passage / gap-out time.";
    }
  }

  grouping phase-timing {
    description
      "Full signalized-intersection phase timing: vehicle timing plus
       pedestrian walk/clearance intervals.";

    uses vehicle-phase-timing;

    leaf walk {
      type uint16;
      units "seconds";
      must ". = 0 or . >= 4" {
        error-message
          "Walk interval must be zero (phase has no pedestrian "
        + "service) or at least 4 seconds per MUTCD section 4E.06.";
      }
      description
        "Walk interval for the associated pedestrian phase.
         Zero means no pedestrian phase is served; otherwise MUTCD
         4E.06 requires at least 4 seconds.";
    }
    leaf ped-clear {
      type uint16;
      units "seconds";
      must "not(../walk) or ../walk = 0 or . >= 1" {
        error-message
          "Pedestrian clearance must be at least 1 second whenever walk is "
        + "served.";
      }
      description
        "Pedestrian clearance (flashing don't walk).  Required
         whenever walk > 0; calculated from crossing distance at
         3.5 ft/s per MUTCD 4E.06.";
    }
  }
}
