module openits-perception-events {
  yang-version 1.1;
  namespace "urn:openits:yang:perception-events";
  prefix openits-pn-events;

  import ietf-yang-types {
    prefix yang;
  }

  import openits-types {
    prefix openits-types;
  }

  import openits-perception {
    prefix openits-pn;
  }

  organization
    "OpenITS Working Group (proposal)";

  contact
    "OpenITS Working Group (proposal)";

  description
    "Notifications for openits-perception.  Split into a companion
     module so ygot's proto backend can generate protobuf from the
     base module (ygot's proto generator fails on modules containing
     notification statements).";

  openits-types:openits-version "0.1.0";

  revision 2026-07-12 {
    description
      "Rename this module (file, module name, namespace, prefix) from
       the legacy notifications-suffixed name to
       openits-perception-events: standardize every service
       notification module on the events-suffixed name. Mechanical
       rename only — no notification content changed; ce-types
       (service-derived, not module-derived) and proto are unaffected.
       Delete the bespoke perception-fault-raised/cleared
       notifications; perception now emits
       openits-common-fault-events:{fault-raised,fault-cleared} with
       kind derived from
       openits-perception-types:perception-fault-event-kind,
       completing the orphan-service fault consolidation.";
  }
  revision 2026-07-11 {
    description
      "Repoint perception-fault-raised's 'category' base from the
       deleted gen-1 openits-pn:fault-category to
       openits-perception-types:perception-fault-event-kind. Breaking:
       identity names change; wire-neutral since the wire
       representation of an identityref is a string (pre-v1,
       acceptable).";
    reference "RFC 7950 section 11 (breaking YANG evolution: identity rename).";
  }
  revision 2026-07-10 {
    description
      "Replace the inline severity enumeration on
       zone-incident-detected and perception-fault-raised with the
       shared openits-types:fault-severity typedef. Member set and
       order unchanged — wire-stable.

       Also, replace the inline latitude/longitude leaves on
       zone-incident-detected with openits-types:geo-point. Already
       fraction-digits 7 — no precision change. Member set and field
       tags unchanged (latitude/longitude keep their locked tags).";
  }
  revision 2026-07-07 {
    description "Initial release.";
  }

  /* --------------------------------------------------------------
   * Notifications
   * -------------------------------------------------------------- */

  notification zone-incident-detected {
    openits-types:arc-it-flow
      "ITS Roadway Equipment -> TMC : incident information";
    description
      "The perception pipeline detected an incident in a configured
       zone.  `incident-id` is stable across the detect / clear pair
       so downstream systems can reconcile.";

    leaf incident-id {
      type string;
      description "Sensor-local incident identifier; stable across detect and clear.";
    }
    leaf zone-id {
      type string;
      description "Zone the incident was detected in.";
    }
    leaf type {
      type identityref {
        base openits-pn:incident-type;
      }
      description "Incident class (stopped-vehicle / wrong-way / pedestrian / debris / spillback / near-miss).";
    }
    leaf severity {
      type openits-types:fault-severity;
      description "Operator-visible severity / priority of the incident.";
    }
    leaf track-id {
      type uint32;
      description "Primary track involved, when the incident is track-scoped.";
    }
    leaf object-class {
      type identityref {
        base openits-pn:object-class;
      }
      description "Classification of the primary track.";
    }
    uses openits-types:geo-point;
    leaf speed-kmh {
      type openits-types:speed-kmh;
      description "Speed of the primary track at detection time.";
    }
    leaf confidence {
      type openits-pn:confidence-percent;
      description "Pipeline confidence in the detection.";
    }
  }

  notification zone-incident-cleared {
    openits-types:arc-it-flow
      "ITS Roadway Equipment -> TMC : incident information";
    description "A previously detected incident is no longer observed.";

    leaf incident-id {
      type string;
      description "The incident-id from the corresponding zone-incident-detected notification.";
    }
    leaf zone-id {
      type string;
      description "Zone the incident was detected in.";
    }
    leaf cleared-at {
      type yang:date-and-time;
      description "Wall-clock time the pipeline stopped observing the incident.";
    }
  }

  notification zone-interval-report {
    openits-types:arc-it-flow
      "ITS Roadway Equipment -> TMC : traffic flow";
    description
      "Periodic per-zone analytics report, emitted once per
       configured data-interval.";

    list zone {
      key "zone-id";
      description "Interval analytics for one configured zone.";

      leaf zone-id {
        type string;
        description "The configured zone this entry reports on.";
      }
      leaf interval-start {
        type yang:date-and-time;
        description "Wall-clock time the reporting interval opened.";
      }
      leaf interval-duration-s {
        type uint16 {
          range "1..3600";
        }
        units "seconds";
        description "Length of the reporting interval.";
      }
      leaf average-speed-kmh {
        type openits-types:speed-kmh;
        description "Mean speed of objects that crossed the zone in the interval.";
      }

      list class-count {
        key "class";
        description "Interval object count broken out per object class.";

        leaf class {
          type identityref {
            base openits-pn:object-class;
          }
          description "Object class this count belongs to.";
        }
        leaf count {
          type uint32;
          units "objects";
          description "Objects of this class observed in the interval.";
        }
      }
    }
  }

}
