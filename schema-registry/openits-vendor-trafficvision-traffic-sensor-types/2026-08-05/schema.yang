module openits-vendor-trafficvision-traffic-sensor-types {
  yang-version 1.1;
  namespace "urn:openits:yang:vendor-trafficvision-traffic-sensor-types";
  prefix openits-vendor-trafficvision-ts-types;

  import openits-traffic-sensor-types {
    prefix openits-traffic-sensor-types;
  }

  import openits-types {
    prefix openits-types;
  }

  organization
    "TrafficVision (vendor)";

  contact
    "OpenITS Working Group (proposal)";

  description
    "Vendor identity module for TrafficVision inactive reasons.
     Declares specialized reasons derived from the open
     openits-traffic-sensor-types:inactive-reason base for the
     TrafficVision-specific conditions that take a video station out
     of service.  A consumer that does not load this module sees the
     base inactive-reason; one that does sees the specific derived
     identity in the same identityref field.

     This module is a reference-implementation worked example of the
     openits vendor-augmentation pattern (identity-only Tier-2,
     docs/06-extension-model.md).  TrafficVision has not ratified
     this file; openits maintains it under the conformance-reference
     NoI until a real TrafficVision-aligned org adopts it.

     Copyright (c) 2026.  Distributed under Apache 2.0.";

  openits-types:openits-version "0.1.0";

  revision 2026-08-05 {
    description
      "Model-review remediation (2026-08): add the openits-version extension
       stamp (and the openits-types import it requires) so this vendor
       module carries the same version marker as its Econolite sibling.
       No schema change.";
  }
  revision 2026-07-21 {
    description
      "Fix truncated revision prose and stale base references in
       descriptions; no schema change.
       Move namespace from urn:trafficvision:… to
       urn:openits:yang:vendor-trafficvision-traffic-sensor-types until
       the vendor formally adopts the module. Wire-neutral for RFC 7951
       JSON (identityref values are module-name-keyed).";
  }
  revision 2026-07-13 {
    description
      "Import openits-traffic-sensor-types (not the openits-traffic-
       sensor service core) and base the four inactive identities on
       openits-traffic-sensor-types:inactive-reason, which moved to the
       -types module. A vendor identity module now depends on
       the lightweight -types layer alone.";
  }
  revision 2026-07-07 {
    description
      "Initial revision.  Declares inactive-low-fps,
       inactive-away-from-preset, inactive-disabled-by-user, and
       inactive-low-view-quality derived from
       openits-traffic-sensor:inactive-reason.";
    reference
      "TrafficVision TMC-3.6 realtime API (inactive_reason values).";
  }

  identity inactive-low-fps {
    base openits-traffic-sensor-types:inactive-reason;
    description
      "TrafficVision station inactive — processed frame rate fell
       below the usable threshold (LOW_FPS).";
  }
  identity inactive-away-from-preset {
    base openits-traffic-sensor-types:inactive-reason;
    description
      "TrafficVision station inactive — the PTZ camera is off its
       calibrated preset (AWAY_FROM_PRESET_*).";
  }
  identity inactive-disabled-by-user {
    base openits-traffic-sensor-types:inactive-reason;
    description
      "TrafficVision station inactive — disabled by the operator
       (DISABLED_BY_USER).";
  }
  identity inactive-low-view-quality {
    base openits-traffic-sensor-types:inactive-reason;
    description
      "TrafficVision station inactive — view quality below the usable
       threshold (AWAY_FROM_PRESET_AND_LOW_VIEW_QUALITY).";
  }
}
