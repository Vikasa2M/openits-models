module openits-types {
  yang-version 1.1;
  namespace "urn:openits:yang:types";
  prefix openits-types;

  import ietf-yang-types {
    prefix yang;
  }

  organization
    "OpenITS Working Group (proposal)";

  contact
    "OpenITS Working Group (proposal)";

  description
    "Shared types, identities, groupings, and the arc-it-flow extension
     for the openits YANG module family. Service-neutral content only;
     service-specific typedefs live in their respective modules.";

  openits-types:openits-version "0.15.0";

  revision 2026-11-09 {
    description
      "Add the device-log case to wire-source, for events decoded from a
       device's own text event log. Additive.";
  }
  revision 2026-10-16 {
    description
      "Add the oper-status typedef, the device-health and
       device-status-summary groupings, the canonical mode-unknown and
       control-unknown identities, and the mode-value-base (values derive
       strictly from the named base) and mandatory-for-kind extensions; clarify control-schedule versus
       control-local-backup. Additive.";
    reference "RFC 7950 §7.19.";
  }

  revision 2026-10-14 {
    description
      "One fault shape for inventories and events. Add the fault-id
       typedef, the component-class identity and the component-ref
       grouping, and reshape fault-entry: typed fault-id and
       correlates-with, a mandatory first-observed, and an optional
       component. Breaking: first-observed is now mandatory.
       Also update descriptions that named the fault inventory's
       category leaf, now kind.";
    reference "RFC 7950 §7.12.";
  }

  revision 2026-10-13 {
    description
      "Give every event a defined stream identity. Add the mandatory
       event-header leaf sequence-epoch, and define sequence as counting
       within one (source-device-id, sequence-epoch) stream. A gap means
       loss only for a consumer receiving the device's full stream.
       Breaking: every producer must emit sequence-epoch.
       Also reword the operational-mode identity description, which
       named mode-changed's old prior/current leaves; now previous-mode
       and mode. Wire-neutral.";
    reference "CloudEvents 1.0 (id).";
  }

  revision 2026-10-12 {
    description
      "Make the fault-severity order normative. The previous caveat said
       the enum inverted the X.733 warning<minor convention and told
       consumers not to compare values across warning and minor; it did
       not invert anything, and the advice pushed every consumer to keep
       a private ranking table. The values are now defined as totally
       ordered, info < warning < minor < major < critical, matching X.733.
       Wire-neutral.";
    reference "ITU-T X.733 §8.1.2.3.";
  }
  revision 2026-09-08 {
    description
      "Hoist the time-source axis into the foundation as an identity.

       Two services modeled the same question with disjoint vocabularies:
       openits-signal-control-types held an identity (ntp / gnss /
       cellular / line-frequency / manual) and openits-rsu-types a closed
       enum (gps / ntp / local / gnss-pps / ptp). A fleet operator asking
       which devices are on holdover had to decode both, and neither
       could name what the other could. Union of the two vocabularies,
       modeled as an identity because clock disciplining is exactly the
       axis a vendor extends -- PTP profiles, a GNSS constellation, a
       holdover oscillator class -- and per the >=3-service placement rule
       it sits in the foundation now that signal-control, RSU, and any
       future device that timestamps what it reports all use it.

       BREAKING (pre-1.0): identityref values are wire strings, so both
       services' producers change what they emit. See the two services'
       revisions of the same date for their migration mappings.

       Also hoists the travel-direction axis, for the same reason and
       from three sources rather than two: reversible-lane held a closed
       enum, work-zone an identity set of its own added days earlier, and
       device-identity-config's own linear-reference a free-form
       'NB'/'SB' string nothing validated. One axis now, with an
       intermediate carriageway-direction base for leaves that can only
       mean a single carriageway -- so reversible-lane's 'direction-a
       must not be unknown' constraint is expressed by the type instead
       of by a must, and work-zone keeps direction-both by typing to the
       wider base. linear-reference/direction is typed to it, replacing
       the string.";
    reference "NTCIP 1201 (global time / time-base); RFC 7950 §11.";
  }
  revision 2026-09-02 {
    description
      "Add the 'geo-path' grouping: an ordered sequence of geo-points
       for features that occupy a length of roadway rather than a point
       on it. The foundation previously carried only 'geo-point' and
       'geo-location', so every linear feature had to define its own
       vertex list -- 'openits-perception' already has one for zone
       vertices. This gives the pattern one definition.

       Additive; no existing node changes.";
    reference "RFC 7950 §11 (additive YANG evolution).";
  }
  revision 2026-08-15 {
    description
      "Hoist the object-class identity hierarchy up from
       openits-perception-types to the foundation layer. Detected-object
       classification is not perception's alone: the zone-occupancy
       capability classifies the population present in a region, and a
       bay sensor that does no tracking must be able to name a truck
       without importing a service core it does not implement
       (docs/08-capability-architecture.md).

       Also clarify object-unknown: it means a classifier ran and was
       not confident, which is distinct from a device that does not
       classify at all and therefore omits the class entirely.

       BREAKING (pre-1.0): identityref values move namespace, so wire
       values change from 'openits-perception-types:object-*' to
       'openits-types:object-*'. Proto tags are unaffected (identityrefs
       render as strings).";
    reference "docs/08-capability-architecture.md.";
  }
  revision 2026-08-05 {
    description
      "Model-review remediation (2026-08): stamp an explicit value
       statement on every enumeration member that lacked one.
       Wire-neutral: each stamped value equals the previous positional
       auto-assignment (RFC 7950 9.6.4.2); this locks the append-only
       enum discipline the wire contract depends on.";
    reference "RFC 7950 9.6.4.2.";
  }
  revision 2026-07-21 {
    description
      "Pre-v1 common-layer cleanup + architecture additions (see per-item
       bullets):
       - wire-source: add 'presence' to container source so it is truly
         optional on notifications while 'decoder' stays mandatory when
         source is present. Fixes the mandatory-decoder contradiction the
         golden fixtures were silently masking.
       - fault-severity: add per-enum descriptions and a normative
         ORDINAL CAVEAT that warning/minor are peer tiers, not ordered.
         Member set/order unchanged — wire-stable.
       - Add the 'mode-change-trigger' base + trigger-* members: the
         open-set cause axis for mode changes (replaces the closed enum
         in openits-common-mode-events:mode-changed/trigger).
       - Move the comm-link-state grouping to openits-device-diagnostics
         (RSU-only; wire-neutral grouping relocation). comm-link-type
         identity stays here (cross-service; needed by the comm-health
         link-type leaf). process/temperature/restart identities remain
         here (moving them is a breaking identityref change deferred
         post-v1).
       - device-hardware: drop per-leaf 'config false'; config-ness now
         comes from the (always config-false) uses context. No semantic
         change — every use site verified under a config-false ancestor.
       - fault-entry: add optional 'correlates-with' (fault-id of a
         related active fault on the same device). Additive.
       - device-identity-config: add optional structured linear-reference
         container + owner/maintained-by/install-date/site-id (DOT/TMDD
         inventory keying). Additive.
       - Add the command-provenance grouping (defined; per-service adoption
         is follow-up). Additive.
       - Add the associated-devices grouping + association-role identities
         (role-qualified device relationships for sensing). Additive.
       - Add canonical intermediate operational-mode identities
         (mode-maintenance / mode-standby-generic / mode-failed-generic)
         for cross-fleet dual-basing. Additive.
       - Collapse duplicate same-date revision statements.
       - control-source: add control-schedule + control-other (ramp NTCIP-1207 axis convergence). Additive.";
  }
  revision 2026-07-14 {
    description
      "Retire the RSU-only system-info grouping: add hardware-version +
       firmware-build to device-hardware (its hardware-identity fields;
       additive, optional) and delete system-info. The runtime fields
       move to openits-device-diagnostics:system-runtime.";
  }
  revision 2026-07-13 {
    description
      "Wave 1 wire-freeze cross-cutting contract fixes (additive):
       - fault-entry 'fault-id': rewrite description to state the
         condition-scoped contract explicitly (stable across raise/
         clear of the SAME condition on the same source-device; the
         pair (source-device-id, fault-id) is unique among a device's
         currently-active faults; reused on re-raise; distinct
         simultaneous instances of the same condition get distinct
         fault-ids), matching the identical contract now stated in
         openits-common-fault-events fault-raised/fault-cleared.
       - 'fault-severity' typedef: rewrite the triage guidance
         (info/warning/minor/major/critical) and add normative
         severity floors (a monitor/conflict-flash MMU fault MUST be
         reported critical). Enum member set unchanged — wire-stable.
       - Add the 'control-source' identity base (control-central,
         control-local-backup, control-manual, control-failed): the
         orthogonal control-authority axis for a device's operating
         mode, distinct from the mode value itself. Carried by
         openits-common-mode-events:mode-changed's new optional
         'control-source' leaf; per-service control-source state
         leaves are deferred to each service's own task.

      Event-envelope wire break (breaking, pre-v1):
       - event-header: add mandatory 'sequence' (uint64) per-source-device
         monotonic counter so same-decisecond hi-res rows have a
         deterministic order; add optional 'observed-by' (poller identity
         for synthesized/observed events) and 'owner' (multi-agency
         device-id qualifier).
       - wire-source: widen indiana-param uint8 -> uint16 to match
         indiana-code (cycle-length and extended-enum params exceed 255).
       - add 'report-event-kind' base under device-event-kind for periodic
         reports.
       - document device-id uniqueness scope and elevation datum (WGS84
         HAE canonical; NTCIP 1204 MSL conversion note).

      Two additive shared groupings that consolidate copy-paste across
       the module family:
       - 'event-header' (source-device-id + occurred-at): the
         identity+timing envelope previously copy-pasted leaf-by-leaf
         into ~20 notifications across 14 modules. Field
         names/types unchanged, so name-locked proto field numbers are
         preserved.
       - 'fault-entry' (fault-id + severity + description +
         first-observed): the common leaves of the config-false
         active-fault list every service exposes. Each service
         'uses fault-entry' and adds its own 'category' identityref.

       Add the percentage-precise typedef (decimal64, 0.0-100.0) and
       the device-hardware grouping; consolidate the duplicate per-
       service percent typedefs onto percentage / percentage-precise.

       Add the operational-mode base identity: the cross-service
       supertype for concrete device operating-mode values (each
       service's mode-value set derives from it), so the generic
       mode-changed notification can carry typed prior/current values.";
    reference "RFC 7950 section 11 (breaking YANG evolution); ATSPM Indiana
       enumeration; SAE J2735 (position datum).";
  }
  revision 2026-07-12 {
    description
      "Remove the 9 signal-control-only first-level bases from
       device-event-kind: phase-event-kind, detector-event-kind,
       overlap-event-kind, pedestrian-event-kind, preemption-
       event-kind, coordination-event-kind, tsp-event-kind,
       tsam-event-kind, external-io-event-kind. These were never
       cross-service — every consumer of them was a signal-control
       sc-<x>-event-kind identity, which already dual-based onto
       openits-signal-control-types:signal-control-event-kind. The
       behavioral grouping they expressed is now carried solely by
       the sc-<x>-event-kind identities under signal-control-
       event-kind, in openits-signal-control-types.

       device-event-kind now keeps only the genuinely cross-service
       first-level bases: fault-event-kind, mode-event-kind,
       comm-health-event-kind. Breaking change (RFC 7950 §11) —
       identities removed. No wire-facing enumeration, notification,
       or generated field is affected: sc-<x>-event-kind identities
       in openits-signal-control-types keep their names, values, and
       single (now sole) base.";
  }
  revision 2026-07-10 {
    description
      "Add the 'fault-severity' typedef (info/warning/minor/major/
       critical), consolidating the identical inline enumeration
       previously copy-pasted across 15 modules (and the local
       typedef in openits-common-fault-events) into one shared
       definition. Member set and order unchanged — wire-stable.
       Additive only.

       Also, add value ranges to previously-unconstrained types:
       speed-kmh (0-400 km/h), dsrc-channel (172-184), and
       geo-location latitude (-90..90) / longitude (-180..180).
       Constraint-tightening only.

       Also, factor 'geo-location' into a new 'geo-point' grouping
       (latitude/longitude, decimal64 fraction-digits 7, ranged
       -90..90 / -180..180) plus elevation/heading; 'geo-location'
       now 'uses geo-point'. Consolidates ~10 inline latitude/
       longitude copy-pastes across modules onto this one grouping
       and corrects a fraction-digits 6-vs-7 precision drift on the
       dms/ess/ramp-metering state-tree sites (frac-6 truncated to
       ~11cm resolution; frac-7 matches the WGS84-standard ~1cm).
       Member set and order unchanged where 'geo-location' was
       already used — wire-stable there; sites converted from inline
       leaves take on the grouping's shape.

       Also, rename SCREAMING_SNAKE_CASE identities to kebab-case per
       RFC 8407 (pre-v1 wire-facing change). Mechanical 1:1 transform;
       no identity added or removed.";
    reference "RFC 8407 section 4.3 (identifier naming).";
  }
  revision 2026-07-08 {
    description
      "Add the 'traffic-density' typedef (vehicles per kilometre of a
       single lane) for per-lane density reporting by traffic-sensor
       detectors.  Additive only — no existing typedef, identity, or
       grouping is renamed or removed.";
    reference
      "RFC 7950 §11 (additive YANG evolution).";
  }
  revision 2026-07-07 {
    description
      "Two additive changes:
       - 'openits-version' extension: a semantic version stamped on
         module content, independent of the revision date. Borrowed
         from OpenConfig's openconfig-version lesson — revision
         dates order changes but cannot signal breaking vs additive
         intent to consumers or tooling.
       - 'plc-register' wire-source case: register-level provenance
         for events decoded from PLC register maps (SRTP, Modbus,
         DNP3), used by the reversible-lane service. Additive choice
         case per RFC 7950 §11.";
    reference
      "OpenConfig openconfig-extensions (openconfig-version
       precedent); RFC 7950 §11 (additive YANG evolution).";
  }
  revision 2026-05-23 {
    description
      "Add 'tsam-event-kind' first-level base under device-event-kind
       so TSAM (Traffic Signal Adaptive Management) sits as a peer
       of TSP rather than under it. TSAM is agency-side adaptive
       optimization; TSP is transit-vehicle-triggered priority —
       distinct domains. Service-specific bases (e.g.,
       sc-tsam-event-kind) will be re-pointed in their home modules.";
  }
  revision 2026-05-16 {
    description
      "Add the cross-service event-taxonomy foundation:
       - 'device-event-kind' identity root for openits's event hierarchy,
         with comm-health/fault/mode/phase/detector/overlap/
         pedestrian/preemption/coordination/tsp/external-io
         first-level bases.
       - 'wire-source' grouping carrying decoder-family + wire identifier
         as YANG-modeled payload (transport-agnostic). Choice cases for
         'indiana', 'ntcip-oid', 'j2735'; future cases extend the choice
         additively (RFC 7950 §11).
       Additive only — no existing identities, typedefs, or groupings
       are renamed or removed.";
    reference
      "RFC 7950 §11 (additive YANG evolution); ATSPM Indiana enumeration
       (wire-source 'indiana' case); NTCIP 1202/1203/1204 ('ntcip-oid'
       case); SAE J2735 ('j2735' case).";
  }
  revision 2026-04-18 {
    description "Initial openits release.";
  }

  /* --------------------------------------------------------------
   * Extensions
   * -------------------------------------------------------------- */

  extension openits-version {
    argument semver;
    description
      "Semantic version of the module's content, independent of the
       YANG revision date.  MAJOR bumps on breaking change (which
       also triggers the 2-year parallel-publish window per
       docs/06-extension-model.md), MINOR on backward-compatible
       additions, PATCH on editorial changes.  Borrowed from
       OpenConfig's openconfig-version practice: revision dates
       order changes but cannot signal compatibility intent.";
  }

  extension arc-it-flow {
    argument flow;
    description
      "Annotates a schema node with the ARC-IT information flow it
       implements.  Argument format:
         '<source-subsystem> -> <destination-subsystem> : <flow-name>'
       Purely informational.  Tooling may walk module trees to emit
       alignment reports for FHWA / ITS JPO review.";
  }

  extension mode-value-base {
    argument identity;
    description
      "Placed on a family's mode-event-kind identity (the identity that
       discriminates that family's mode space on a mode-changed
       notification). The argument names the identity, as
       '<prefix>:<identity-name>', that every previous-mode and mode
       value carried by a mode-changed notification of that kind MUST
       derive from (strictly: the base itself is not a value). It binds
       the family's kind to its own mode vocabulary, so a signal-control kind cannot carry a DMS
       mode value. Tooling and conformance checks enforce it; the
       YANG type system alone cannot, because mode is a single
       identityref based on operational-mode.";
  }

  extension mandatory-for-kind {
    argument leaf-and-identity;
    description
      "Placed on a notification. Argument format:
         '<leaf-name> <prefix:identity>'
       The named leaf of the notification is mandatory when the
       notification's kind derives from (or equals) the named
       identity, and optional otherwise. It expresses a
       kind-conditional mandatory leaf that a plain 'mandatory true'
       cannot, because the leaf applies to some kinds and not others.
       The leaf-name is a direct child of the notification. Tooling
       (the notification mandatory-leaf checker) enforces it on
       instances.";
  }

  /* --------------------------------------------------------------
   * Generic typedefs
   * -------------------------------------------------------------- */

  typedef device-id {
    type string {
      length "1..64";
      pattern '[a-zA-Z0-9_-]+';
    }
    description
      "Device identifier, unique within a single operator's deployment.
       Multi-agency deployments qualify uniqueness with event-header
       'owner'. Carried in the event payload (not only the transport
       envelope) so it survives any transport per the repo's
       payload-survivability rule.";
  }

  typedef percentage {
    type uint8 {
      range "0..100";
    }
    units "percent";
    description "Whole-number percentage value from 0 to 100.";
  }

  typedef percentage-precise {
    type decimal64 {
      fraction-digits 1;
      range "0.0 .. 100.0";
    }
    units "percent";
    description
      "Percentage value from 0.0 to 100.0 with 0.1 resolution, for
       quantities that need sub-percent precision (humidity, occupancy,
       etc.). Use 'percentage' where whole-number precision suffices.";
  }

  typedef heading-degrees {
    type uint16 {
      range "0..359";
    }
    units "degrees";
    description "Compass heading in degrees (0 = North)";
  }

  typedef speed-kmh {
    type decimal64 {
      fraction-digits 1;
      range "0.0 .. 400.0";
    }
    units "km/h";
    description "Speed in kilometers per hour";
  }

  typedef traffic-density {
    type decimal64 {
      fraction-digits 1;
      range "0.0 .. 250.0";
    }
    units "veh/km";
    description
      "Traffic density — vehicles present per kilometre of a single
       lane.  250 veh/km upper bound covers jam density with margin.";
  }

  typedef fault-id {
    type string {
      length "1..128";
    }
    description
      "Device-local fault identifier, condition-scoped: stable across
       raise and clear of the same condition on the same device, and
       reused if the condition recurs after clearing. Distinct
       simultaneous instances of one condition take distinct ids.
       Consumers correlate and deduplicate on (source-device-id,
       fault-id).";
  }

  typedef fault-severity {
    type enumeration {
      enum info { value 0; description "Informational only; no operator action required."; }
      enum warning { value 1; description "Monitor / threshold-approach: watch, may raise a low-priority work order. Less severe than minor."; }
      enum minor { value 2; description "Confirmed single-component fault (one detector, one pixel); raises a work order."; }
      enum major { value 3; description "Degraded service across the device."; }
      enum critical { value 4; description "Safety-relevant; dispatch now."; }
    }
    description
      "Severity of a fault/alert, shared across all openits services.
       Triage: info = FYI only; warning = monitor/threshold-approach;
       minor = a confirmed single-component fault; major = degraded
       service; critical = safety-relevant, dispatch now.
       Normative floors: a monitor/conflict-flash (MMU) fault MUST be
       reported critical. Vendors MUST NOT down-rate below these floors.
       ORDERING: the values are totally ordered by severity,
       info < warning < minor < major < critical, and the enum values
       follow that order, so a consumer MAY sort, threshold or compare
       on the value. This matches the ITU-T X.733 perceived-severity
       order (warning < minor < major < critical); info sits below
       warning for notices that need no action.";
    reference "ITU-T X.733 §8.1.2.3 (perceived severity).";
  }

  typedef oper-status {
    type enumeration {
      enum unknown { value 0; description "The operational condition is not known."; }
      enum ok { value 1; description "Operating normally."; }
      enum degraded { value 2; description "Operating, but with reduced function or capacity."; }
      enum failed { value 3; description "Not performing its function."; }
      enum not-present { value 4; description "The device or unit is not installed or not detected."; }
    }
    description
      "Operational condition of a device: whether it is performing its
       function. It is the operational condition only.
       Administrative state (enabled, disabled, in service) belongs in
       configuration or in a maintenance mode, not here. Reachability
       belongs to comm-health: an unreachable device keeps its last
       reported oper-status, which the comm-loss rule marks stale; it
       does not become failed or unknown because the link dropped.
       An absent oper-status means unknown, never ok: a consumer MUST
       NOT infer a healthy device from the absence of this leaf.";
  }

  /* --------------------------------------------------------------
   * Shared identities
   * -------------------------------------------------------------- */

  identity component-class {
    description
      "Base for the kinds of sub-component a fault or mode change can
       name: a phase, a detector, a lamp module, a gate, a radio. Each
       service, and each platform module, derives its own classes. The
       foundation defines none, so a consumer branches on a class the
       service published rather than on a fault-id string.";
  }

  identity process-state { description "Base identity for process states"; }
  identity proc-running  { base process-state; description "Process is running"; }
  identity proc-stopped  { base process-state; description "Process is stopped"; }
  identity proc-starting { base process-state; description "Process is starting"; }
  identity proc-stopping { base process-state; description "Process is stopping"; }
  identity proc-crashed  { base process-state; description "Process has crashed"; }

  identity temperature-status { description "Base identity for temperature status"; }
  identity temp-normal        { base temperature-status; description "Normal operating temperature"; }
  identity temp-high          { base temperature-status; description "High temperature warning"; }
  identity temp-low           { base temperature-status; description "Low temperature warning"; }
  identity temp-critical-high { base temperature-status; description "Critical high temperature"; }
  identity temp-critical-low  { base temperature-status; description "Critical low temperature"; }

  identity restart-reason         { description "Base identity for system restart reasons"; }
  identity restart-power-cycle    { base restart-reason; description "Power cycle restart"; }
  identity restart-watchdog       { base restart-reason; description "Watchdog timer restart"; }
  identity restart-manual         { base restart-reason; description "Manual restart"; }
  identity restart-upgrade        { base restart-reason; description "Firmware upgrade restart"; }
  identity restart-config-change  { base restart-reason; description "Configuration change restart"; }
  identity restart-fault-recovery { base restart-reason; description "Fault recovery restart"; }
  identity restart-scheduled      { base restart-reason; description "Scheduled restart"; }

  identity comm-link-type { description "Base identity for communication link types"; }
  identity link-ethernet  { base comm-link-type; description "Ethernet link"; }
  identity link-serial    { base comm-link-type; description "Serial link (RS-232/RS-485)"; }
  identity link-cellular  { base comm-link-type; description "Cellular modem link"; }
  identity link-wifi      { base comm-link-type; description "WiFi link"; }
  identity link-fiber     { base comm-link-type; description "Fiber optic link"; }
  identity link-dialup    { base comm-link-type; description "Dial-up modem link"; }

  /* --------------------------------------------------------------
   * Detected-object classification
   *
   * A property of a detected object, NOT an event: object-class is a
   * standalone root and deliberately does NOT derive from
   * device-event-kind, so derived-from-or-self(device-event-kind)
   * (the "every event" filter) does not return object classes.
   *
   * Foundation-layer because more than one capability classifies what
   * it detects: perception classifies tracked objects, zone-occupancy
   * classifies the population present in a region. A sensor that only
   * reports what is parked in a bay must be able to name a truck
   * without importing a tracking service core it does not implement.
   * -------------------------------------------------------------- */

  identity object-class {
    description "Root identity for detected-object classification.";
  }
  identity object-passenger-vehicle { base object-class; description "Passenger car, SUV, pickup, or van."; }
  identity object-truck             { base object-class; description "Single-unit or combination truck."; }
  identity object-bus               { base object-class; description "Transit or intercity bus."; }
  identity object-motorcycle        { base object-class; description "Motorcycle or moped."; }
  identity object-bicycle           { base object-class; description "Bicycle or e-bike."; }
  identity object-pedestrian        { base object-class; description "Person on foot."; }
  identity object-animal            { base object-class; description "Animal in or near the roadway."; }
  identity object-debris            { base object-class; description "Stationary foreign object in the roadway."; }
  identity object-unknown {
    base object-class;
    description
      "The object is detected but the classifier has no confident class.
       Distinct from the class being absent: a device that cannot
       classify at all omits the class rather than reporting this
       value, so a consumer can tell 'unclassifiable by a classifier
       that ran' from 'nothing here classifies'.";
  }

  /* --------------------------------------------------------------
   * Device-event-kind identity hierarchy
   *
   * Root for the cross-service event taxonomy. Every event a device
   * emits — in any service (signal-control, dms, ess, rsu, ramp-
   * metering, perception, traffic-sensor, reversible-lane) — is
   * identified by an identityref pointing to a derived identity below.
   *
   * First-level bases here are genuinely cross-service behavioral
   * classes so a downstream consumer can filter generically
   * (derived-from-or-self fault-event-kind = every fault, across
   * every service) or specifically (derived-from-or-self
   * vendor:econolite-vendor-alarm = one vendor identity).
   * Service-specific event modules derive their own bases below
   * these.
   *
   * Behavioral classes used by only one service (e.g., signal-
   * control's phase/detector/overlap/pedestrian/preemption/
   * coordination/tsp/tsam/external-io events) live under that
   * service's own root instead (e.g.,
   * openits-signal-control-types:signal-control-event-kind) rather
   * than here.
   *
   * Adding a new first-level base here is a backward-compatible
   * additive YANG change. Removing or renaming one is a breaking
   * change and requires a major revision bump.
   *
   * NOTE: Identities below use kebab-case per RFC 8407 §4.3, as do all
   * other identities in this module (process-state, restart-reason,
   * comm-link-type, temperature-status). New identities — in this
   * module or any other openits module — MUST use kebab-case.
   * -------------------------------------------------------------- */

  identity device-event-kind {
    description
      "Root identity for every openits event across every service.
       Service-specific event modules derive sub-bases from this root.";
  }

  identity comm-health-event-kind {
    base device-event-kind;
    description
      "Communication-health events: link state, time drift,
       comm-attempt statistics. Applies to every device.";
  }

  identity fault-event-kind {
    base device-event-kind;
    description
      "Generic fault events: a device reports a fault condition.
       Service-specific identities derive from this for service-
       specific fault catalogs (signal-controller cabinet faults,
       DMS pixel faults, RSU radio faults, etc.).";
  }

  identity mode-event-kind {
    base device-event-kind;
    description
      "Operational-mode-change events: a device transitions between
       operational modes (signal-controller normal/coordinated/free/
       flash, ramp-meter active/inactive, etc.).";
  }

  identity report-event-kind {
    base device-event-kind;
    description
      "Periodic-report events: a device emits a scheduled aggregate/
       status report (interval volume/occupancy, station status, plan
       applied) rather than a discrete state change. Service report
       identities derive from this so a consumer can filter every
       periodic report across the catalog with
       derived-from-or-self(report-event-kind).";
  }

  identity operational-mode {
    description
      "Cross-service base identity for a concrete device operating-mode
       *value* (as opposed to mode-event-kind, which discriminates the
       mode *space* on a mode-changed notification). Each service's
       mode-value set derives from this base (openits-dms-types:
       sign-mode, openits-ramp-metering-types:meter-mode,
       openits-signal-control-types:controller-mode,
       openits-rsu-types:rsu-mode), so the generic
       openits-common-mode-events:mode-changed notification can carry
       typed, enumerable previous-mode/mode values via a single
       identityref instead of free-form strings.";
  }

  identity mode-maintenance {
    base operational-mode;
    description
      "Canonical cross-service 'in maintenance / out of service for
       servicing' mode. A service's maintenance-equivalent value MAY add
       this as a SECOND base (dual-basing, mirroring the event-kind dual
       classification) so a fleet filter derived-from-or-self(
       mode-maintenance) spans services without enumerating per-family
       values.";
  }
  identity mode-unknown {
    base operational-mode;
    description
      "Canonical cross-service 'operating mode not known' value. Used
       when a device cannot report which mode it is in, for example a
       first report before the mode is determined. It is not a mode
       the device is in, and never means normal operation; a family
       whose mode-changed values are bound by mode-value-base MAY
       dual-base its own unknown value on this identity.";
  }
  identity mode-standby-generic { base operational-mode; description "Canonical cross-service standby / armed-but-idle mode for fleet-wide filtering; family standby values dual-base on this."; }
  identity mode-failed-generic  { base operational-mode; description "Canonical cross-service failed / faulted operating mode for fleet-wide filtering; family failed values dual-base on this."; }

  identity control-source {
    description
      "Orthogonal control-source axis for a device's operating mode:
       which authority is currently driving it. Distinct from the mode
       VALUE (what it's doing) — a signal on local TOD backup after
       comm loss and one under central coordination both read
       'coordinated' but differ here.";
  }

  identity control-central {
    base control-source;
    description "Driven by central/TMC command.";
  }

  identity control-local-backup {
    base control-source;
    description
      "Fallback: running on local logic after loss of central control
       (comm loss or a central-system failure). Unplanned, and it ends
       when central control resumes. Distinct from control-schedule,
       where operating from a schedule is the design.";
  }

  identity control-manual {
    base control-source;
    description "Under manual/field control (technician/police panel).";
  }

  identity control-failed {
    base control-source;
    description "Control authority indeterminate/failed.";
  }

  identity control-schedule {
    base control-source;
    description
      "Operating by design from the device's time-of-day / schedule
       authority (NTCIP TOD), with no loss of central control implied.
       Distinct from control-local-backup, which is a fallback after
       central control is lost.";
  }

  identity control-unknown {
    base control-source;
    description
      "Canonical 'control authority not known' value, for a device
       that cannot report which authority is driving it. Distinct from
       control-failed (authority indeterminate because control failed)
       and control-other (a known authority not otherwise classified).";
  }

  identity control-other {
    base control-source;
    description "Control authority not otherwise classified.";
  }

  identity travel-direction {
    description
      "Which direction of travel a fact applies to. The axis, including
       the aggregate and unknown answers a feed legitimately publishes;
       a leaf that can only mean one carriageway narrows to
       carriageway-direction below rather than restating the exclusion
       as a must.

       Foundation-layer because three surfaces asked the same question
       three different ways before this: reversible-lane held a closed
       enum, work-zone an identity set of its own, and
       device-identity-config's linear-reference a free-form string of
       'NB'/'SB' abbreviations nothing validated. Cardinal, not relative
       to a linear reference: a consumer holding WGS84 geometry and an
       opaque id cannot resolve 'increasing measure' to a carriageway,
       and cardinal direction is what WZDx and TMDD both publish.";
    reference "WZDx v4 (RoadEventCoreDetails.direction).";
  }

  identity carriageway-direction {
    base travel-direction;
    description
      "Exactly one direction of travel. A leaf typed to this base admits
       no aggregate or unknown value, so 'this names a single
       carriageway' is enforced by the type rather than by a must the
       next author has to remember to write.";
  }
  identity direction-northbound { base carriageway-direction; description "Traffic traveling north."; }
  identity direction-southbound { base carriageway-direction; description "Traffic traveling south."; }
  identity direction-eastbound  { base carriageway-direction; description "Traffic traveling east."; }
  identity direction-westbound  { base carriageway-direction; description "Traffic traveling west."; }
  identity direction-inner-loop {
    base carriageway-direction;
    description
      "The inner carriageway of a ring road, where cardinal direction
       changes along the route and so cannot name a carriageway.";
    reference "WZDx v4 (direction: inner-loop).";
  }
  identity direction-outer-loop {
    base carriageway-direction;
    description "The outer carriageway of a ring road; counterpart to direction-inner-loop.";
    reference "WZDx v4 (direction: outer-loop).";
  }

  identity direction-both {
    base travel-direction;
    description
      "Both directions are affected. A positive claim that both
       carriageways are involved, which real feeds publish and a model
       that cannot carry it pushes back onto the translator.";
  }
  identity direction-unknown {
    base travel-direction;
    description
      "The publisher did not report a direction. Distinct from
       direction-both: this says nothing is known, and a consumer must
       not widen it into a claim about both carriageways.";
    reference "WZDx v4 (direction: unknown).";
  }

  identity time-source {
    description
      "How a device's real-time clock is disciplined. An identity rather
       than a closed enum because a vendor can legitimately ship a source
       the core has not catalogued -- PTP profiles, a specific GNSS
       constellation, a holdover oscillator class -- without the core
       being wrong.

       Foundation-layer because the axis is not one service's: a signal
       controller, an RSU and any future device that timestamps what it
       reports all answer the same question, and a fleet operator asking
       'what is on holdover' should not have to decode two vocabularies.
       Hoisted here from openits-signal-control-types, which held the
       only identity form while openits-rsu-types held a disjoint closed
       enum for the same concept.";
    reference "NTCIP 1201 (global time / time-base).";
  }
  identity time-source-ntp            { base time-source; description "Network Time Protocol server."; }
  identity time-source-gnss           { base time-source; description "GNSS/GPS receiver, without explicit 1PPS disciplining."; }
  identity time-source-gnss-pps       { base time-source; description "GNSS receiver disciplined by a 1PPS signal -- the accuracy class J2735 TimeMarks require."; }
  identity time-source-ptp            { base time-source; description "IEEE 1588 Precision Time Protocol."; }
  identity time-source-cellular       { base time-source; description "Cellular-network time."; }
  identity time-source-line-frequency { base time-source; description "AC line-frequency clock."; }
  identity time-source-manual         { base time-source; description "Manually set, free-running clock."; }
  identity time-source-local {
    base time-source;
    description
      "Free-running local clock with no external discipline. NOT
       UTC-traceable: a device on this source must not be trusted for
       any timestamp a consumer correlates across devices, which is why
       openits-rsu forbids it while SPaT is broadcasting.";
  }

  identity mode-change-trigger {
    description
      "Machine-readable cause of an operational-mode change, beside the
       free-form 'reason' and orthogonal to control-source (authority)
       and command-provenance (actor). Open set — new causes are added
       as derived identities (non-breaking, identityref serialises as a
       module-qualified string).";
  }
  identity trigger-operator   { base mode-change-trigger; description "Operator-initiated."; }
  identity trigger-schedule   { base mode-change-trigger; description "Time-of-day / schedule-initiated."; }
  identity trigger-fault      { base mode-change-trigger; description "Fault-initiated fallback."; }
  identity trigger-preemption { base mode-change-trigger; description "Preemption / priority-initiated."; }
  identity trigger-comm-loss  { base mode-change-trigger; description "Loss-of-communications fallback."; }
  identity trigger-adaptive   { base mode-change-trigger; description "Adaptive / optimization-initiated."; }
  identity trigger-unknown    { base mode-change-trigger; description "Cause not reported."; }

  /* --------------------------------------------------------------
   * Shared groupings
   * -------------------------------------------------------------- */

  grouping geo-point {
    description "WGS84 latitude/longitude for any device or observation.";
    leaf latitude  { type decimal64 { fraction-digits 7; range "-90.0 .. 90.0"; }   description "WGS84 latitude in decimal degrees"; }
    leaf longitude { type decimal64 { fraction-digits 7; range "-180.0 .. 180.0"; } description "WGS84 longitude in decimal degrees"; }
  }

  grouping geo-location {
    description "Geographic location for any device: a WGS84 point plus optional elevation and heading.";
    uses geo-point;
    leaf elevation {
      type decimal64 { fraction-digits 1; }
      units "meters";
      description
        "Elevation as WGS84 ellipsoidal height (height above ellipsoid,
         HAE) — the canonical datum here, matching SAE J2735 position
         payloads. NOTE: NTCIP 1204 ESS reports mean-sea-level (MSL)
         elevation, which differs from HAE by the local geoid undulation
         (~-30 m across CONUS); convert MSL->HAE at the decoder.
         DOT practice often reports NAVD88 orthometric height; NAVD88
         relates to HAE via the geoid model, a separate offset from the
         MSL note above.";
    }
    leaf heading   { type heading-degrees; description "Orientation heading in degrees from north"; }
  }

  grouping geo-path {
    description
      "An ordered sequence of WGS84 points describing a linear extent
       along the roadway -- the shape of a closure, a segment, or any
       feature that occupies road rather than a spot on it.

       A one-point path is a degenerate point, and that is deliberate:
       real roadway-event feeds routinely publish a closure as a single
       coordinate with no extent, and a model that cannot carry that
       forces the translator to either invent a second point or drop the
       feature. Consumers must handle a single-element path.

       Ordering is carried by an explicit key rather than
       'ordered-by user'. The generated protobuf is what crosses the
       wire, and a repeated field's order is not a guarantee any
       consumer should have to assume -- an explicit index survives
       re-encoding, partial application, and any intermediary that sorts
       by key.

       The key is 'point-index' rather than 'sequence' because
       'event-header' already contributes a top-level 'sequence' leaf to
       every notification, and two unrelated meanings of that word in
       one payload is a trap.";
    list point {
      key "point-index";
      description "One point along the path, in ascending point-index order.";
      leaf point-index {
        type uint16;
        description
          "Position along the path, ascending from the feature's start,
           from 0. Gaps are permitted -- a translator may drop a point
           it cannot place without renumbering the rest.";
      }
      uses geo-point;
    }
  }

  grouping device-hardware {
    description
      "Manufacturer-reported hardware identity of any device: make,
       model, firmware, serial number, hardware version, and firmware
       build. Config-free grouping (RFC 8407 §4.13) — config-ness is set
       by the 'uses' context, which is always a config-false state
       subtree. Every service's identity container 'uses' this instead
       of re-inlining the same leaves.";
    leaf make     { type string; description "Manufacturer name reported by the device."; }
    leaf model    { type string; description "Model identifier reported by the device."; }
    leaf firmware { type string; description "Firmware version reported by the device."; }
    leaf serial   { type string; description "Hardware serial number reported by the device."; }
    leaf hardware-version { type string; description "Hardware version reported by the device."; }
    leaf firmware-build   { type string; description "Firmware build identifier reported by the device."; }
  }

  grouping device-identity-config {
    description
      "Shared operator-provisioned device identity: id, name, road reference,
       and geographic location. Used in a service's config container (intended)
       and mirrored in its state container (applied). Device-reported hardware
       (device-hardware) is a separate state-only uses.";
    leaf id {
      type device-id;
      description
        "Agency-internal device identifier (URN tail). Same charset as the
         event-header source-device-id, so a device can always be named in
         its own events.";
    }
    leaf name { type string; description "Operator-facing device name."; }
    leaf road-reference {
      type string;
      description
        "Free-form route / location reference (e.g., \"I-35 NB @ MP 214\").
         Informational only.";
    }
    uses geo-location;
    container linear-reference {
      presence "A structured linear-referencing location is provided.";
      description
        "Structured linear referencing (route + milepost / LRS measure) —
         how state DOTs and TMDD key device location. Optional; complements
         the free-form road-reference.";
      leaf route-designator { type string; description "Route/highway designator (e.g. 'I-35', 'US-40', 'SR-135')."; }
      leaf direction {
        type identityref {
          base carriageway-direction;
        }
        description
          "Travel direction along the route. A single carriageway by
           construction, since a milepost on a divided route belongs to
           one of them; typed rather than the free-form 'NB'/'SB' string
           it was, which nothing validated and every consumer parsed by
           convention.";
      }
      leaf measure          { type decimal64 { fraction-digits 3; } units "miles"; description "Milepost / linear measure along the route."; }
      leaf lrs-method       { type string; description "Linear-referencing method / network id the measure is expressed in (agency LRS)."; }
    }
    leaf owner        { type string; description "Owning agency / jurisdiction for this device (inventory-level; distinct from the event-header 'owner' qualifier)."; }
    leaf maintained-by { type string; description "Agency / contractor responsible for maintaining this device."; }
    leaf install-date { type yang:date-and-time; description "Date the device was installed / commissioned."; }
    leaf site-id      { type string; description "Cabinet / site identifier housing this device."; }
  }

  grouping command-provenance {
    description
      "Shared audit-trail envelope for a command / write-path action: who
       issued it, under what authority, and when. DEFINED here; per-service
       ADOPTION is follow-up work (not in this plan). Intended adopters:
       DMS message activation (owner/active-source), CCTV holder
       (requested-by/current-holder), ramp plan selection, reversible-lane
       last-command-source, and mode-changed. Distinct axes: actor-id =
       WHO, actor-class = under which AUTHORITY (reuses control-source),
       schedule-id = the schedule that drove it.";
    leaf actor-id     { type string; description "Identifier of the actor that issued the command (operator id, workflow id, schedule owner). Agency-scoped free-form."; }
    leaf actor-class  { type identityref { base control-source; } description "Authority class the actor acted under (reuses the control-source axis)."; }
    leaf schedule-id  { type string; description "Schedule / plan id when the command was schedule-driven."; }
    leaf commanded-at { type yang:date-and-time; description "Wall-clock time the command was issued."; }
  }

  identity association-role  { description "Base identity for how one device relates to another."; }
  identity role-verifies      { base association-role; description "This device verifies against the related device."; }
  identity role-verified-by   { base association-role; description "This device is verified by the related device."; }
  identity role-co-located    { base association-role; description "The related device is physically co-located."; }
  identity role-same-platform { base association-role; description "The related device shares the same physical platform / enclosure."; }
  identity role-upstream      { base association-role; description "The related device is upstream of this one in the traffic flow."; }
  identity role-downstream    { base association-role; description "The related device is downstream of this one in the traffic flow."; }

  grouping associated-devices {
    description
      "Optional role-qualified references from one device to related
       openits devices, so a perception / traffic-sensor / camera state
       subtree can name the device it verifies against, a co-located
       device, or an up/down-stream device — without an external
       inventory join.";
    list associated-device {
      key "device-id role";
      description "One related device, qualified by relationship role.";
      leaf device-id { type device-id; description "The related device's id (same charset as source-device-id)."; }
      leaf role      { type identityref { base association-role; } description "How the related device relates to this one."; }
      leaf note      { type string; description "Optional free-form note about the association."; }
    }
  }

  /* --------------------------------------------------------------
   * Event-notification header
   *
   * The identity + timing envelope shared by every openits event
   * notification. A notification declares its own 'kind' identityref
   * (the identity base differs per service, so 'kind' is not part of
   * this grouping), then 'uses event-header' for the device + time,
   * and — for events decoded from a wire encoding — 'uses wire-source'
   * for provenance. Consolidates the source-device-id/occurred-at pair
   * that was previously hand-copied into every notification.
   * -------------------------------------------------------------- */

  grouping event-header {
    description
      "Common device + timing envelope for an openits event
       notification: the device the event pertains to and the
       wall-clock time it occurred at that device. Notifications add
       their own 'kind' identityref and, for wire-decoded events,
       'uses openits-types:wire-source'.";

    leaf source-device-id {
      type device-id;
      mandatory true;
      description
        "Device this event pertains to, using the openits-types:
         device-id pattern '[a-zA-Z0-9_-]+'. Typically the
         controller-id / sign-id / RSU-id from the inventory.";
    }

    leaf occurred-at {
      type yang:date-and-time;
      mandatory true;
      description
        "Wall-clock time the event occurred at the device. Distinct
         from CloudEvents ce-time (when the publisher observed it); the
         two diverge for HR-log backfill or when device NTP is broken.";
    }

    leaf sequence {
      type uint64;
      mandatory true;
      description
        "Event counter within one stream. A stream is one
         (source-device-id, sequence-epoch) pair. Within a stream the
         producer increments sequence by exactly 1 for each event it
         emits, in emission order. A different sequence-epoch is a
         different stream that starts fresh; it is not loss.

         Consumers order a stream's events by sequence, and by
         (occurred-at, sequence) across ties such as the high-resolution
         rows that share one decisecond tick. A gap within one stream
         indicates loss only for a consumer that receives the device's
         full event stream. A consumer subscribed to a subset of the
         device's subjects MUST NOT infer loss from gaps.

         Not part of event identity: ce-id excludes it.";
    }

    leaf sequence-epoch {
      type string {
        length "1..64";
      }
      mandatory true;
      description
        "Opaque name of the stream this event's sequence belongs to. A
         producer mints a new epoch whenever its counter can restart:
         a device reboot, a collector restart, or failover to a
         different producer. Two redundant producers watching one device
         therefore emit two epochs; their duplicate events still collapse
         by ce-id, which excludes this leaf.

         Consumers MUST compare epochs for equality only; the value has
         no order and no internal structure.";
    }

    leaf observed-by {
      type device-id;
      description
        "Device/poller that OBSERVED this event, when different from
         source-device-id. Present on synthesized events a collector
         infers rather than the source reporting (e.g. comm-loss, which
         is necessarily observed by the poller, not emitted by the
         unreachable device). Absent when the source device reported the
         event itself. For observer-reported events, occurred-at is the
         observer's clock.";
    }

    leaf owner {
      type string;
      description
        "Optional owning organization/agency for source-device-id, for
         multi-agency deployments where device-id uniqueness is scoped
         per operator. Free-form agency identifier; TMDD-style org
         qualification. Absent in single-operator deployments.";
    }
  }

  /* --------------------------------------------------------------
   * Fault-inventory entry
   *
   * One entry in a device's live active-fault list (the config-false
   * 'faults' container every service exposes). A service's fault list
   * 'uses fault-entry' for the common leaves and adds its own
   * service-specific 'kind' identityref (base
   * <service>-fault-event-kind), so a fleet-wide
   * derived-from-or-self(fault-event-kind) filter spans every service.
   * -------------------------------------------------------------- */

  grouping component-ref {
    description
      "Names the sub-component an event or fault concerns. Absent when
       it concerns the device as a whole.";
    container component {
      presence
        "The fault or event concerns one sub-component of the device.";
      description
        "The sub-component, as a (class, id) pair a consumer joins to
         the live-state list for that class.";
      leaf component-class {
        type identityref {
          base component-class;
        }
        mandatory true;
        description "What kind of sub-component this is.";
      }
      leaf component-id {
        type string {
          length "1..128";
        }
        mandatory true;
        description
          "The key of the referenced live-state list entry. A composite
           key is its key values joined by '/' in key order.";
      }
    }
  }

  grouping device-health {
    description
      "Cross-service health of a device, placed on a device's root
       state. Carries operational condition and freshness only; it
       holds no mode and no kind, which stay with the service.";
    leaf oper-status {
      type oper-status;
      description
        "Operational condition of the device. Absent means unknown,
         never ok.";
    }
    leaf last-change {
      type yang:date-and-time;
      description
        "When oper-status last changed value.";
    }
    leaf observed-at {
      type yang:date-and-time;
      description
        "The time of this health reading. A consumer compares it
         with the reporting cadence to judge how fresh the reading
         is.";
    }
  }

  grouping device-status-summary {
    description
      "The shared shape of a device's periodic status summary: health,
       which authority controls it, how long it has been up, and how
       many faults are active. It carries no mode; the mode of a
       family is reported by that family.";
    leaf oper-status {
      type oper-status;
      description
        "Operational condition of the device at observed-at. Absent
         means unknown, never ok.";
    }
    leaf control-source {
      type identityref {
        base control-source;
      }
      description
        "Which authority is currently driving the device. Absent
         means not reported; control-unknown means the device could
         not tell.";
    }
    leaf uptime-s {
      type uint64;
      units "seconds";
      description
        "Seconds since the device last started.";
    }
    leaf active-fault-count {
      type uint32;
      description
        "Number of faults currently active on the device.";
    }
    leaf observed-at {
      type yang:date-and-time;
      description
        "The time of this reading. A consumer compares it with the
         reporting cadence to judge how fresh the summary is.";
    }
  }

  grouping fault-entry {
    description
      "One active fault: the leaves a service's live fault inventory
       and the fault-raised notification share. The classifier is not
       here: an inventory types its own kind leaf to the service's fault
       base, and fault-raised types its kind to the cross-service
       base.";

    leaf fault-id {
      type fault-id;
      description
        "Device-local fault identifier (see the fault-id typedef). The
         key of the enclosing inventory list.";
    }
    leaf severity {
      type fault-severity;
      description "Operator-visible severity of the fault.";
    }
    leaf description {
      type string;
      description "Human-readable fault description from the device.";
    }
    leaf correlates-with {
      type fault-id;
      description
        "Optional fault-id of another active fault on the same device
         that this fault is causally related to, so a consumer can
         collapse a fault storm to its root.";
    }
    leaf first-observed {
      type yang:date-and-time;
      mandatory true;
      description
        "When the fault was first observed: the device's own time when
         it reports one, otherwise the time the producer first saw the
         fault. Consumers key a fault occurrence on (source-device-id,
         fault-id, first-observed).";
    }
    uses component-ref;
  }

  /* --------------------------------------------------------------
   * Wire-source provenance
   *
   * Every event that originates from a decoded wire encoding carries
   * this grouping in its YANG-modeled payload. Transport-agnostic by
   * design: it appears in the payload, not in any envelope, so a
   * consumer reading over NATS, REST, NETCONF, or gNMI sees the
   * wire identifier identically.
   *
   * The 'tag' choice gives type-safe per-decoder-family variants
   * (Indiana enumeration for ATSPM HR logs, NTCIP OIDs for SNMP-poll
   * decoders, J2735 messageId for V2X RSU traffic). New decoder
   * families add new cases additively per RFC 7950 §11.
   * -------------------------------------------------------------- */

  grouping wire-source {
    description
      "Wire-level provenance: the original identifier the event was
       decoded from. Optional on notifications — events synthesized
       inside openits rather than decoded off a wire leave it absent.";

    container source {
      presence
        "Present iff this event was decoded from a wire encoding.
         Absent for events synthesized inside openits. When present,
         'decoder' is mandatory.";
      description "Wire-level provenance of this event.";

      leaf decoder {
        type string;
        mandatory true;
        description
          "Decoder-family name. Convention: lowercase, hyphenated.
           Examples: 'indiana' (ATSPM Indiana enumeration HR logs),
           'ntcip-1202' (NTCIP 1202 signal-controller MIB),
           'ntcip-1203' (NTCIP 1203 DMS MIB),
           'ntcip-1204' (NTCIP 1204 ESS MIB),
           'j2735' (SAE J2735 V2X messages),
           'srtp' / 'modbus' / 'dnp3' (PLC register maps),
           'device-text-log' (a device's own text event log),
           'gnmi-subscribe' (future), 'snmp-trap' (future).";
      }

      choice tag {
        description
          "Decoder-family-specific wire identifier. Additive: new
           decoder families add new cases without breaking existing
           consumers.";

        case indiana {
          description
            "ATSPM 'Indiana enumeration' HR event vocabulary (used by
             Econolite ASC3, McCain MaxTime, Trafficware ATC, and
             Yunex controllers).";
          reference
            "ATSPM Indiana enumeration (HR event-code vocabulary).";
          leaf indiana-code {
            type uint16;
            description
              "Indiana event-code from the controller's HR log row.";
          }
          leaf indiana-param {
            type uint16;
            description
              "Indiana event-param (phase number, detector channel,
               preempt number, etc. — meaning depends on event-code).
               uint16 to match indiana-code width: params such as the
               new cycle length in seconds (Indiana 132) and extended
               MaxTime/ATC enum values exceed 255.";
          }
        }

        case ntcip-oid {
          description
            "NTCIP MIB objects polled via SNMP. OID + stringified raw
             value.";
          reference
            "NTCIP 1202 (signal-control MIB); NTCIP 1203 (DMS MIB);
             NTCIP 1204 (ESS MIB).";
          leaf oid {
            type string;
            description "Dotted-numeric OID, e.g., '1.3.6.1.4.1.1206.4.2.1.1.1'.";
          }
          leaf oid-value {
            type string;
            description
              "Stringified raw value the OID held at poll time.";
          }
        }

        case j2735 {
          description
            "SAE J2735 V2X messages. messageId per DSRC.MessageFrame.";
          reference "SAE J2735 (DSRC.MessageFrame.messageId).";
          leaf message-id {
            type uint16;
            description "J2735 MessageFrame.messageId.";
          }
        }

        case plc-register {
          description
            "PLC register reads (SRTP, Modbus, DNP3, or similar
             register-map protocols), used by facility PLCs such as
             reversible-lane controllers. The decoder leaf names the
             concrete protocol ('srtp', 'modbus', 'dnp3'); this case
             carries register + stringified raw value.";
          leaf register {
            type string;
            description
              "PLC register reference in the controller's native
               notation, e.g., '%R00100' (SRTP) or '40001' (Modbus).";
          }
          leaf register-value {
            type string;
            description
              "Stringified raw value the register held at read time.";
          }
        }

        case device-log {
          description
            "An entry from a device's own text event log: the log a
             controller, sign or sensor keeps for its operators, as
             opposed to a coded HR log. The decoder leaf names the log
             reader; the event header's occurred-at is the time the
             device gave the entry.";
          leaf log-name {
            type string {
              length "1..64";
            }
            description
              "Which of the device's logs the entry came from, in the
               device's own naming, when it keeps more than one.";
          }
          leaf log-text {
            type string {
              length "1..1024";
            }
            description
              "The entry's text exactly as the device recorded it,
               including any time or date text the device put in the
               line. A producer undoes any encoding the transport added
               to carry the text, and changes nothing else.";
          }
        }
      }
    }
  }
}
