module openits-reversible-lane {
  yang-version 1.1;
  namespace "urn:openits:yang:reversible-lane";
  prefix openits-rl;

  import ietf-yang-types {
    prefix yang;
  }

  import openits-types {
    prefix openits-types;
  }

  import openits-reversible-lane-types {
    prefix openits-reversible-lane-types;
  }

  organization
    "OpenITS Working Group (proposal)";

  contact
    "OpenITS Working Group (proposal)";

  description
    "YANG data model for reversible-lane facilities — corridors,
     bridges, and tunnels whose lanes carry traffic in either of two
     opposing directions under operator control.

     Aligned with ARC-IT 9.1 service package TM16 (Reversible Lane
     Management).  Facilities of this class are typically driven by
     a PLC exposing lane state through a register map; the model is
     transport-independent, so SRTP, Modbus, DNP3, or NTCIP adapters
     map onto it identically.  Wire provenance for register-decoded
     events rides in the openits-types wire-source 'plc-register'
     case.  Vendor-specific capabilities ride in vendor augment
     modules per docs/06-extension-model.md, never in this module.

     The facility is a four-state machine.  With direction-a =
     northbound and direction-b = southbound, the operator-visible
     states map to: Open NB (open + northbound), Open SB (open +
     southbound), Closed, and In-Transition.  Directions are
     configured per facility so east-west corridors use the same
     model.

     Structured per the config/state idiom: every commanded surface
     (facility `config` directions, `control/config`, and each lane's
     `segments/segment/lane/config`) is config true and every
     readback (`state`, `control/state`, and each lane's
     `segments/segment/lane/state`) is config false, one per lane per
     MUTCD Chapter 4M (a lane-use control signal governs a single
     lane, not a whole segment).

     This is a safety-critical control model.  `must` constraints on
     every commanded, config-true surface forbid unsafe or
     inconsistent writes and conforming controllers MUST refuse
     writes that violate them:
       - the facility's two travel directions must be concrete and
         cardinal opposites (`config/direction-a` /
         `config/direction-b`);
       - an open target-state must name a target-direction that is
         one of the facility's configured directions
         (`control/config`);
       - per lane, a commanded green-arrow or flashing-yellow-X
         toward one direction requires a commanded steady red-X
         toward the other (`segments/segment/lane/config`) — the
         green-implies-opposing-red-X invariant.
     The config-false readback (`state`, `control/state`,
     `segments/segment/lane/state`) carries no `must`: it reports
     anomalies — including a lane reading back green-arrow to both
     directions — as data plus a fault/alarm, not as illegal data;
     a misbehaving facility's telemetry must stay representable so
     it can be reported (see lcs-conflict-detected).

     Copyright (c) 2026.  Distributed under Apache 2.0.";

  openits-types:openits-version "0.4.0";

  revision 2026-08-05 {
    description
      "Model-review remediation (2026-08): stamp an explicit value
       statement on every enumeration member that lacked one.
       Wire-neutral: each stamped value equals the previous positional
       auto-assignment (RFC 7950 9.6.4.2); this locks the append-only
       enum discipline the wire contract depends on.";
    reference "RFC 7950 9.6.4.2.";
  }
  revision 2026-07-21 {
    description
      "Interlock evaluation points (safety): add
       interlocks/interlock/config/evaluation-point (changeover-start |
       direction-open, mandatory) so pre-start gates (lockout-clear,
       intrusion-clear) and mid-sequence gates (sweep-confirmed,
       red-x-confirmed, gate-agreement) evaluate at the right phase;
       redefine control/state/changeover-permitted as the start gate and
       add control/state/direction-open-permitted as the open gate. A
       conforming controller MUST NOT enter transition phase lcs-reverse
       (green/FYX toward the new direction) while direction-open-permitted
       is false. BREAKING (pre-v1): interlock configs must add
       evaluation-point. Add control/config/min-clearance-duration-s and
       min-verification-dwell-s (minimum clearance / verification dwell,
       tied normatively to the direction-open gate). Set
       control/state/blocking-interlocks leafref require-instance false
       (state readback must not be illegal data).
       - Collapse duplicate same-date revision statements.
       - Re-document last-command-source as the command-provenance actor-id (not an authority). No wire change.";
    reference "MUTCD 11th ed. Chapter 4M; ARC-IT 9.1 TM16.";
  }
  revision 2026-07-15 {
    description
      "Changeover clearance gate: restructure interlocks into a declared
       config set (typed kind + required flag) plus config-false
       satisfied state, and add control/state/changeover-permitted +
       blocking-interlocks so 'refuse a changeover unless cleared' is
       machine-observable instead of prose; append locked / manual-release
       to gate-state. BREAKING (pre-v1): the interlocks subtree changes
       from a flat config-false list (all-satisfied + interlock) to a
       config/state paired list; all-satisfied is dropped in favour of the
       required-subset changeover-permitted rollup.";
    reference "MUTCD 11th ed. Chapter 4M; ARC-IT 9.1 TM16.";
  }
  revision 2026-07-14 {
    description
      "Cut 3c (events layering): move typedefs travel-direction,
       lane-flow-state, and lcs-indication to
       openits-reversible-lane-types so the events module imports
       only -types, not this core. All in-module uses (direction-a,
       direction-b, target-direction, open-direction, from-direction,
       to-direction, current-state, lcs-direction-a, lcs-direction-b)
       re-prefixed accordingly. Wire-neutral (a typedef emits no
       proto); pre-v1 consumers repoint the prefix.";
  }
  revision 2026-07-13 {
    description
      "Strip the config-false state musts from state (open-direction
       presence) and segments/segment (dual green-arrow). A must on
       config-false readback made a misbehaving facility's telemetry
       illegal data instead of a reportable condition: an open
       facility with no open-direction and a segment reading
       green-arrow to both directions are now representable, the
       latter being exactly the condition lcs-conflict-detected
       exists to report. No schema change; must-only removal.

      Adopt the shared openits-types:fault-entry grouping in the
       config-false faults list, replacing the inline fault-id +
       severity + description + first-observed leaves. The
       service-specific category identityref is unchanged.

       Also adopt the shared openits-types:device-hardware grouping
       (make/model/firmware/serial) in the identity container,
       replacing the inline config-false leaves.";
  }
  revision 2026-07-11 {
    description
      "Move the fault taxonomy to gen-2: delete the gen-1
       fault-category identity and its fault-plc-communication /
       fault-interlock / fault-conflict / fault-gate / fault-lcs-head /
       fault-power children, replaced by the service-prefixed
       reversible-lane-fault-event-kind tree in the new
       openits-reversible-lane-types module. The
       reversible-lane-event-kind service root also moves to
       openits-reversible-lane-types. The faults/fault 'category' leaf
       now bases on
       openits-reversible-lane-types:reversible-lane-fault-event-kind.
       Breaking: identity names change (e.g. fault-plc-communication
       -> reversible-lane-fault-plc-communication); wire-neutral since
       the wire representation of an identityref is a string (pre-v1,
       acceptable).

      Add the reversible-lane-event-kind service root and give the
       service's event-kind roots that base, completing the service
       dimension of the cross-service event-kind taxonomy. Additive
       (identities gain a base); no identity renamed or removed.";
    reference
      "RFC 7950 section 11 (breaking YANG evolution: identity rename).;
      RFC 7950 section 11 (additive YANG evolution).";
  }
  revision 2026-07-10 {
    description
      "Replace the inline severity enumeration on the fault-inventory
       list with the shared openits-types:fault-severity typedef.
       Member set and order unchanged — wire-stable.

       Also, add base openits-types:fault-event-kind to the
       fault-category root so this service's faults are reachable by
       fleet-wide derived-from-or-self(fault-event-kind) queries.
       Additive (identity gains a base); no child renamed.";
    reference "RFC 7950 section 11 (additive YANG evolution).";
  }
  revision 2026-07-07 {
    description
      "Initial revision.  Minimum viable model covering identity,
       commanded state, live state machine, transition progress,
       per-segment lane-control-signal heads and gates, interlocks,
       and a live fault inventory.";
    reference
      "ARC-IT 9.1 Service Package TM16 (Reversible Lane Management);
       MUTCD 11th Ed. Chapter 4M (Lane-Use Control Signals).";
  }

  /* --------------------------------------------------------------
   * Typedefs
   * -------------------------------------------------------------- */

  typedef gate-state {
    type enumeration {
      enum unknown { value 0; }
      enum open    { value 1; }
      enum closed  { value 2; }
      enum moving  { value 3; }
      enum fault   { value 4; }
      enum locked         { value 5; description "Gate mechanically locked out (manual)."; }
      enum manual-release { value 6; description "Gate under manual release / local control."; }
    }
    description "Physical barrier-gate position.";
  }

  /* --------------------------------------------------------------
   * Main tree
   * -------------------------------------------------------------- */

  container reversible-lane {
    description
      "Top-level container for a single reversible-lane facility.";

    /* ----- identity ----- */
    container config {
      description
        "Intended facility identity + the two opposing travel
         directions.";
      uses openits-types:device-identity-config;

      leaf direction-a {
        type openits-reversible-lane-types:travel-direction;
        must ". != 'unknown'" {
          error-message "direction-a must be a concrete direction";
        }
        description
          "First of the two opposing travel directions this facility
           serves (e.g., northbound).";
      }
      leaf direction-b {
        type openits-reversible-lane-types:travel-direction;
        must "(../direction-a='northbound' and .='southbound') or (../direction-a='southbound' and .='northbound')
           or (../direction-a='eastbound' and .='westbound') or (../direction-a='westbound' and .='eastbound')" {
          error-message
            "direction-b must be the cardinal opposite of direction-a (NB<->SB or EB<->WB).";
        }
        description
          "Second, opposing travel direction this facility serves
           (e.g., southbound).";
      }
    }
    container state {
      config false;
      openits-types:arc-it-flow
        "ITS Roadway Equipment -> TMC : lane management status";
      description
        "Applied facility identity (mirror) + device-reported
         hardware.";
      uses openits-types:device-identity-config;
      uses openits-types:device-hardware;
    }

    /* ----- control ----- */
    container control {
      description
        "Commanded facility changeover.  Write control/config to
         request a changeover; control/state reports the running
         sequence and result.  Applied-vs-commanded is config/state
         divergence.  The controller MUST refuse a changeover while
         control/state/changeover-permitted is false (a required
         interlock unsatisfied).";

      container config {
        openits-types:arc-it-flow
          "TMC -> ITS Roadway Equipment : lane management control";
        // GUARD (default-tree must): transition-timeout-s carries a default (900),
        // which materialises control/config in the implicit default tree. This
        // must's antecedent `not(target-state='open')` is TRUE when target-state
        // is absent (default tree), so it passes vacuously today. If target-state
        // is ever given a default of 'open', this safety must would begin firing
        // on the default tree for every fixture — re-guard before doing so.
        must "not(target-state = 'open') or boolean(target-direction)" {
          error-message "an open target-state must name target-direction";
        }
        description "Requested facility changeover.";

        leaf target-state {
          type enumeration {
            enum closed { value 1; }
            enum open   { value 2; }
          }
          description "Requested end state of the facility.";
        }
        leaf target-direction {
          type openits-reversible-lane-types:travel-direction;
          must ". = ../../../config/direction-a or . = ../../../config/direction-b" {
            error-message
              "target-direction must be one of the facility's configured directions";
          }
          description
            "Requested open direction.  Meaningful only when
             target-state is `open`.";
        }
        leaf transition-timeout-s {
          type uint16 {
            range "30..7200";
          }
          units "seconds";
          default "900";
          description
            "Maximum allowed changeover duration.  Exceeding it
             raises the transition-timeout notification and a fault
             as appropriate.";
        }
        leaf min-clearance-duration-s {
          type uint16 { range "1..600"; }
          units "seconds";
          description
            "Minimum time the clearance indications (yellow-X / flashing-yellow-X)
             must be shown before the facility may be treated as clear. A
             conforming controller MUST hold clearance at least this long; an
             instantaneous clearance does not satisfy the direction-open gate.";
        }
        leaf min-verification-dwell-s {
          type uint16 { range "1..600"; }
          units "seconds";
          description
            "Minimum dwell for which all direction-open interlocks must remain
             continuously satisfied before direction-open-permitted may go true.
             Phase order: clearance (min-clearance-duration-s) -> sweep/gate
             verification (min-verification-dwell-s with direction-open
             interlocks satisfied) -> lcs-reverse toward the new direction.";
        }
      }

      container state {
        config false;
        openits-types:arc-it-flow
          "ITS Roadway Equipment -> TMC : lane management status";
        description
          "Live facility state as read back from the PLC.  An `open`
           facility that reads back no open-direction is a reportable
           telemetry fault, not illegal data.";

        leaf current-state {
          type openits-reversible-lane-types:lane-flow-state;
          description "Current position in the facility state machine.";
        }
        leaf open-direction {
          type openits-reversible-lane-types:travel-direction;
          description
            "Direction currently open to traffic.  Present iff
             current-state is `open`.";
        }
        leaf last-command-source {
          type string;
          description
            "Actor that issued the most recent state command — the
             command-provenance actor-id (operator id, automation workflow),
             NOT a control-authority class. Full 'uses
             openits-types:command-provenance' adoption is follow-up.";
        }
        leaf last-command-at {
          type yang:date-and-time;
          description "Wall-clock time of the most recent state command.";
        }
        leaf changeover-permitted {
          type boolean;
          description
            "START gate: true when every REQUIRED interlock whose evaluation-point
             is changeover-start is satisfied. A conforming controller MUST refuse
             a changeover command while this is false; the blocking interlocks are
             listed in blocking-interlocks.";
        }
        leaf direction-open-permitted {
          type boolean;
          description
            "OPEN gate: true when every REQUIRED interlock (both
             changeover-start and direction-open) is satisfied. A conforming
             controller MUST NOT enter transition phase lcs-reverse — MUST NOT
             drive any lane to green-arrow or flashing-yellow-X toward the new
             direction — while this is false. Supersets changeover-permitted.";
        }
        leaf-list blocking-interlocks {
          type leafref { path "../../../interlocks/interlock/interlock-id"; require-instance false; }
          description
            "Interlock-ids of required interlocks not currently satisfied
             — the reason a changeover is refused.";
        }

        container transition {
          description
            "Progress of the running changeover.  Empty when
             current-state is not `in-transition`.";

          leaf phase {
            type enumeration {
              enum requested     { value 0; }
              enum clearance     { value 1; }
              enum sweep-verify  { value 2; }
              enum gate-movement { value 3; }
              enum lcs-reverse   { value 4; }
              enum complete      { value 5; }
            }
            description
              "Explicit changeover phase (structured; supersedes
               free-form step names for the standard sequence).
               clearance is the yellow-X / flashing-yellow-X shown
               while closing a direction; sweep-verify confirms the
               facility is empty; lcs-reverse reverses the LCS heads
               to the new direction; entered only after
               direction-open-permitted is true.";
          }
          leaf from-direction {
            type openits-reversible-lane-types:travel-direction;
            description "Direction open when the changeover started.";
          }
          leaf to-direction {
            type openits-reversible-lane-types:travel-direction;
            description
              "Direction (or closure) the changeover is moving
               toward.";
          }
          leaf started-at {
            type yang:date-and-time;
            description "Wall-clock time the changeover sequence started.";
          }
          leaf sequence-step {
            type string;
            description
              "Optional vendor-specific step label; informational
               only.";
          }
        }
      }
    }

    /* ----- segments ----- */
    container segments {
      description
        "Per-segment, per-lane lane-use control signals: commanded
         (config) + readback (state).";

      list segment {
        key "segment-id";
        description "One gated / signed section of the facility.";

        leaf segment-id {
          type leafref {
            path "../config/segment-id";
          }
          description "Facility-local segment identifier (key).";
        }
        container config {
          description "Segment identity.";
          leaf segment-id {
            type string {
              length "1..64";
            }
            description "Facility-local segment identifier.";
          }
          leaf name {
            type string;
            description "Operator-facing segment description.";
          }
        }

        list lane {
          key "lane-id";
          description "One lane-use control signal per lane (MUTCD 4M).";

          leaf lane-id {
            type leafref {
              path "../config/lane-id";
            }
            description "Segment-local lane identifier (key).";
          }
          container config {
            description
              "COMMANDED lane-use control signals for this lane.  The
               safety invariant is enforced here: an unsafe commanded
               pair is rejected.";
            must "not(lcs-direction-a = 'green-arrow' or lcs-direction-a = 'flashing-yellow-x') or lcs-direction-b = 'red-x'" {
              error-message
                "A green-arrow or flashing-yellow-X toward direction-a requires a steady red-X toward direction-b (MUTCD 4M).";
            }
            must "not(lcs-direction-b = 'green-arrow' or lcs-direction-b = 'flashing-yellow-x') or lcs-direction-a = 'red-x'" {
              error-message
                "A green-arrow or flashing-yellow-X toward direction-b requires a steady red-X toward direction-a (MUTCD 4M).";
            }

            leaf lane-id {
              type string {
                length "1..64";
              }
              description "Segment-local lane identifier.";
            }
            leaf lcs-direction-a {
              type openits-reversible-lane-types:lcs-indication;
              description "Commanded LCS indication facing direction-a traffic.";
            }
            leaf lcs-direction-b {
              type openits-reversible-lane-types:lcs-indication;
              description "Commanded LCS indication facing direction-b traffic.";
            }
          }
          container state {
            config false;
            description
              "Actual LCS readback for this lane.  Constraint-free: a
               lane reading green-arrow to both directions is the
               exact conflict lcs-conflict-detected exists to report
               and MUST be representable.";

            leaf lcs-direction-a {
              type openits-reversible-lane-types:lcs-indication;
              description "Actual LCS indication facing direction-a traffic.";
            }
            leaf lcs-direction-b {
              type openits-reversible-lane-types:lcs-indication;
              description "Actual LCS indication facing direction-b traffic.";
            }
            leaf gate-state {
              type gate-state;
              description "Barrier-gate position for this lane, if gated.";
            }
          }
        }
      }
    }

    /* ----- interlocks ----- */
    container interlocks {
      description
        "The facility's declared changeover interlock set (config) and
         their live satisfaction (state). A required interlock that is
         not satisfied blocks a changeover — see
         control/state/changeover-permitted (MUTCD 4M / ARC-IT TM16).";

      list interlock {
        key "interlock-id";
        description "One declared interlock precondition.";

        leaf interlock-id {
          type leafref { path "../config/interlock-id"; }
          description "Facility-local interlock identifier (key).";
        }
        container config {
          description "Declared interlock: what it is and whether it gates a changeover.";
          leaf interlock-id {
            type string { length "1..64"; }
            description "Facility-local interlock identifier.";
          }
          leaf kind {
            type identityref { base openits-reversible-lane-types:interlock-kind; }
            mandatory true;
            description
              "Typed interlock precondition (sweep-confirmed,
               gate-agreement, ingress-secured, intrusion-clear, ...).";
          }
          leaf name {
            type string;
            description "Operator-facing interlock description.";
          }
          leaf required {
            type boolean;
            default "true";
            description
              "When true, a changeover is refused until this interlock is
               satisfied.";
          }
          leaf evaluation-point {
            type enumeration {
              enum changeover-start { value 0; description "Gate evaluated BEFORE a changeover may start — a rest-state precondition (e.g. lockout-clear, intrusion-clear)."; }
              enum direction-open { value 1; description "Gate evaluated DURING the sequence before the new direction may be opened (e.g. sweep-confirmed, red-x-confirmed, gate-agreement)."; }
            }
            mandatory true;
            description
              "When this interlock gates the changeover: changeover-start gates
               are rest-state preconditions checked before the sequence begins;
               direction-open gates are mid-sequence preconditions that MUST hold
               before any lane may show green/flashing-yellow-X toward the new
               direction (transition phase lcs-reverse).";
          }
        }
        container state {
          config false;
          openits-types:arc-it-flow
            "ITS Roadway Equipment -> TMC : lane management status";
          description "Live interlock satisfaction.";
          leaf satisfied {
            type boolean;
            description "The interlock currently permits a changeover.";
          }
        }
      }
    }

    /* ----- fault inventory ----- */
    container faults {
      config false;
      openits-types:arc-it-flow
        "ITS Roadway Equipment -> Maintenance : equipment maintenance status";
      description
        "Live fault inventory.  Each entry mirrors a
         `reversible-lane-fault-raised` notification and clears when
         the condition resolves.";

      list fault {
        key "fault-id";
        description "One entry per active fault at the facility.";

        uses openits-types:fault-entry;
        leaf category {
          type identityref {
            base openits-reversible-lane-types:reversible-lane-fault-event-kind;
          }
          description "Fault class (plc-communication / interlock / conflict / gate / lcs-head / power).";
        }
      }
    }
  }
}
