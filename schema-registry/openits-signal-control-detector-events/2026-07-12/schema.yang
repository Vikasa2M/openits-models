module openits-signal-control-detector-events {
  yang-version 1.1;
  namespace "urn:openits:yang:signal-control-detector-events";
  prefix openits-sc-det;

  import ietf-yang-types {
    prefix yang;
  }

  import openits-types {
    prefix openits-types;
  }

  import openits-signal-control-types {
    prefix openits-sc-types;
  }

  organization
    "OpenITS Working Group (proposal)";

  contact
    "OpenITS Working Group (proposal)";

  description
    "Signal-controller vehicle and TSP detector transition + fault
     notifications. Each notification carries a 'kind' identityref
     derived from openits-signal-control-types:sc-detector-event-kind
     and a 'wire-source' grouping.";

  revision 2026-07-12 {
    description
      "Add detector-report (periodic per-detector volume/occupancy
       aggregate. Additive.";
  }

  revision 2026-05-17 {
    description
      "Initial revision. Hosts the detector-transition notification
       migrated from the signal-control notifications companion module@2026-05-15.";
    reference "ATSPM Indiana enumeration (detector event codes).";
  }

  /* --------------------------------------------------------------
   * Notifications
   * -------------------------------------------------------------- */

  notification detector-transition {
    openits-types:arc-it-flow
      "Roadway Signal Controller -> ATSPM / TMC : vehicle detection";
    description
      "A vehicle detector channel changed state. The 'kind' identityref
       names the specific transition (on, off, restored, or a fault
       class); 'wire-source' carries the original Indiana wire identifier.";

    leaf kind {
      type identityref { base openits-sc-types:sc-detector-event-kind; }
      mandatory true;
      description "Specific detector-transition identity from the Indiana taxonomy.";
    }
    leaf source-device-id {
      type openits-types:device-id;
      mandatory true;
      description "Controller hosting this detector channel.";
    }
    leaf channel { type uint32; mandatory true; description "Detector channel number on the controller."; }
    leaf transition {
      type enumeration {
        enum unspecified; enum on; enum off; enum restored;
        enum fault-other; enum fault-watchdog; enum fault-open-loop;
        enum fault-shorted-loop; enum fault-excessive-change;
      }
      description
        "What the channel did: on/off transition, restoration, or a
         specific fault class (watchdog, open-loop, shorted-loop,
         excessive-change).";
    }
    leaf lane         { type string; description "Inventory-enriched lane label."; }
    leaf approach     { type string; description "Inventory-enriched approach label."; }
    leaf phase-served { type uint8;  description "Phase this detector calls."; }
    leaf occurred-at {
      type yang:date-and-time;
      mandatory true;
      description "Wall-clock time the detector transition occurred at the controller.";
    }

    uses openits-types:wire-source;
  }

  notification detector-report {
    openits-types:arc-it-flow
      "Roadway Signal Controller -> ATSPM / TMC : traffic detector data";
    description
      "Periodic per-detector volume/occupancy aggregate, one entry per
       detector channel, emitted once per configured data interval.
       Distinct from detector-transition, which fires on each individual
       detector state change.";

    leaf source-device-id {
      type openits-types:device-id;
      mandatory true;
      description "Controller hosting these detector channels.";
    }
    leaf interval-start {
      type yang:date-and-time;
      description "Wall-clock time the reporting interval opened.";
    }
    leaf interval-duration-s {
      type uint16 { range "1..3600"; }
      units "seconds";
      description "Length of the reporting interval.";
    }
    list detector {
      key "detector-id";
      description "Interval aggregate for one detector channel.";

      leaf detector-id {
        type uint16;
        description "Controller-local detector channel number.";
      }
      leaf phase-served {
        type uint8;
        description "Phase this detector calls (0 if unassigned).";
      }
      leaf volume {
        type uint32;
        units "vehicles";
        description "Vehicle count over the interval.";
      }
      leaf occupancy {
        type openits-types:percentage;
        description "Detector occupancy over the interval (0-100%).";
      }
    }
    leaf occurred-at {
      type yang:date-and-time;
      mandatory true;
      description "Wall-clock time the report was generated at the controller.";
    }
  }
}
