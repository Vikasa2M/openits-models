module enum-collision-a {
  namespace "urn:test:enum-collision-a";
  prefix eca;

  // Paired with enum-collision-b.yang for TestEmit_enumNoCrossModuleCollision:
  // both modules declare an inline `enumeration` on a same-named leaf
  // ("state") with different, partially-overlapping value sets, mirroring
  // the real prior/current collision between openits-rsu-events and
  // openits-signal-control-events.

  notification event-a {
    leaf state {
      type enumeration {
        enum idle;
        enum active;
        enum fault;
      }
      description "State before/after some module-a transition.";
    }
  }
}
