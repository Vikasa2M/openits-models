module nested-collision-fixture {
  yang-version 1.1;
  namespace "urn:openits:test:nestedcollision";
  prefix nc;

  container device {
    container alpha {
      list sensor { key id; leaf id { type string; } leaf a { type uint32; } }
    }
    container beta {
      list sensor { key id; leaf id { type string; } leaf b { type uint32; } }
    }
  }
}
