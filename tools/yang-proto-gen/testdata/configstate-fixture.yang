module configstate-fixture {
  yang-version 1.1;
  namespace "urn:openits:test:configstate";
  prefix cs;

  container signal-controller {
    container config {
      leaf controller-mode { type string; }
    }
    container state {
      config false;
      leaf controller-mode { type string; }
      leaf uptime { type uint32; }
    }
    list phase {
      key "phase-id";
      leaf phase-id {
        type leafref { path "../config/phase-id"; }
      }
      container config {
        leaf phase-id { type uint32; }
        leaf min-green { type uint32; }
      }
      container state {
        config false;
        leaf phase-id { type uint32; }
        leaf min-green { type uint32; }
        leaf elapsed-seconds { type uint32; }
      }
    }
  }
}
