module openits-types {
  yang-version 1.1;
  namespace "urn:test:openits-types";
  prefix ot;

  extension mode-value-base {
    argument identity;
    description "Test copy of the mode-value-base extension.";
  }

  identity device-event-kind;
  identity mode-event-kind {
    base device-event-kind;
  }
  identity operational-mode;
  identity mode-unknown {
    base operational-mode;
  }
}
